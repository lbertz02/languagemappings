module ts29274-messages-f40-2 {

namespace "urn:onf:params:xml:ns:yang:ts29274:f:messages";
prefix "gtp";

import ts29274-ies-f40 {	
	prefix "gtp_ies";
}

import ts29280-ies-f00 {
	prefix "sv_ies";
}

description "Messages defined in 3GPP TS 29.274 (verision f40).

   Copyright 2018 Lyle Bertz.

   Licensed under the Apache License, Version 2.0 (the \"License\");
   you may not use this file except in compliance with the License.
   You may obtain a copy of the License at

       http://www.apache.org/licenses/LICENSE-2.0

   Unless required by applicable law or agreed to in writing, software
   distributed under the License is distributed on an \"AS IS\" BASIS,
   WITHOUT WARRANTIES OR CONDITIONS OF ANY KIND, either express or implied.
   See the License for the specific language governing permissions and
   limitations under the License.";

extension intsancenum {
	description "The instance number of the IE in the message";
	argument "number";
}

extension messageTypeValue {
	description "The eGTP Message Type number";
	argument "number";
}

extension messageType {
	description "GTP Message Type.  It is one of Request, Response, Notification, Acknowledge or Indication";
    argument "string";
}

extension iemandatory {
	description "Indicates that the IE (container) is mandatory";
}

extension containingMessage {
	description "Notes the message that contains the specific grouped IE subtype.";
	argument "number";
}

grouping echo_request {
	gtp:messageType "request";
	gtp:messageTypeValue 1;
	container recovery {
		uses gtp_ies:recovery;
		gtp_ies:order 1;
		gtp:iemandatory;
		gtp:intsancenum 0;
	}
	container sending_node_features {
		uses gtp_ies:node_features;
		gtp_ies:order 2;
		gtp:intsancenum 0;
		description "This IE shall be sent towards a peer node on any GTPv2 interface if the sending node supports at least one feature on this interface or if the sending node supports at least one feature and does not know the interface type towards the peer node. This IE may be present otherwise. 
";
	}
	container private_extension {
		uses gtp_ies:private_extension;
		gtp_ies:order 3;
	}
}
grouping echo_response {
	gtp:messageType "response";
	gtp:messageTypeValue 2;
	container recovery {
		uses gtp_ies:recovery;
		gtp_ies:order 1;
		gtp:iemandatory;
		gtp:intsancenum 0;
	}
	container sending_node_features {
		uses gtp_ies:node_features;
		gtp_ies:order 2;
		gtp:intsancenum 0;
		description "This IE shall be sent towards a peer node on any GTPv2 interface if the sending node supports at least one feature on this interface or if the sending node supports at least one feature and does not know the interface type towards the peer node. This IE may be present otherwise.
";
	}
	container private_extension {
		uses gtp_ies:private_extension;
		gtp_ies:order 3;
	}
}
grouping create_session_request {
	gtp:messageType "request";
	container imsi {
		uses gtp_ies:imsi;
		gtp_ies:order 1;
		gtp:intsancenum 0;
	}
	container msisdn {
		uses gtp_ies:msisdn;
		gtp_ies:order 2;
		gtp:intsancenum 0;
	}
	container me_identity {
		uses gtp_ies:mei;
		gtp_ies:order 3;
		gtp:intsancenum 0;
	}
	container user_location_information {
		uses gtp_ies:uli;
		gtp_ies:order 4;
		gtp:intsancenum 0;
	}
	container rat_type {
		uses gtp_ies:rat_type;
		gtp_ies:order 5;
		gtp:iemandatory;
		gtp:intsancenum 0;
	}
	container indication_flags {
		uses gtp_ies:indication;
		gtp_ies:order 6;
		gtp:intsancenum 0;
	}
	container sender_fteid_for_control_plane {
		uses gtp_ies:fteid;
		gtp_ies:order 7;
		gtp:iemandatory;
		gtp:intsancenum 0;
	}
	container pgw_s5s8_address_for_control_plane_or_pmip {
		uses gtp_ies:fteid;
		gtp_ies:order 8;
		gtp:intsancenum 1;
	}
	container access_point_name {
		uses gtp_ies:apn;
		gtp_ies:order 9;
		gtp:iemandatory;
		gtp:intsancenum 0;
	}
	container selection_mode {
		uses gtp_ies:selection_mode;
		gtp_ies:order 10;
		gtp:intsancenum 0;
	}
	container pdn_type {
		uses gtp_ies:pdn_type;
		gtp_ies:order 11;
		gtp:intsancenum 0;
	}
	container pdn_address_allocation {
		uses gtp_ies:paa;
		gtp_ies:order 12;
		gtp:intsancenum 0;
	}
	container maximum_apn_restriction {
		uses gtp_ies:apn_restriction;
		gtp_ies:order 13;
		gtp:intsancenum 0;
	}
	container aggregate_maximum_bit_rate {
		uses gtp_ies:ambr;
		gtp_ies:order 14;
		gtp:intsancenum 0;
	}
	container linked_eps_bearer_id {
		uses gtp_ies:ebi;
		gtp_ies:order 15;
		gtp:intsancenum 0;
	}
	container trusted_wlan_mode_indication {
		uses gtp_ies:twmi;
		gtp_ies:order 16;
		gtp:intsancenum 0;
	}
	container protocol_configuration_options {
		uses gtp_ies:pco;
		gtp_ies:order 17;
		gtp:intsancenum 0;
	}
	container bearer_contexts_to_be_created {
		uses gtp_ies:bearer_context;
		gtp_ies:order 18;
		gtp:iemandatory;
		gtp:intsancenum 0;
	}
	container bearer_contexts_to_be_removed {
		uses gtp_ies:bearer_context;
		gtp_ies:order 19;
		gtp:intsancenum 1;
	}
	container trace_information {
		uses gtp_ies:trace_information;
		gtp_ies:order 20;
		gtp:intsancenum 0;
	}
	container recovery {
		uses gtp_ies:recovery;
		gtp_ies:order 21;
		gtp:intsancenum 0;
	}
	container mmefqcsid {
		uses gtp_ies:fqcsid;
		gtp_ies:order 22;
		gtp:intsancenum 0;
	}
	container sgwfqcsid {
		uses gtp_ies:fqcsid;
		gtp_ies:order 23;
		gtp:intsancenum 1;
	}
	container epdgfqcsid {
		uses gtp_ies:fqcsid;
		gtp_ies:order 24;
		gtp:intsancenum 2;
	}
	container twanfqcsid {
		uses gtp_ies:fqcsid;
		gtp_ies:order 25;
		gtp:intsancenum 3;
	}
	container ue_time_zone {
		uses gtp_ies:ue_time_zone;
		gtp_ies:order 26;
		gtp:intsancenum 0;
	}
	container user_csg_information {
		uses gtp_ies:uci;
		gtp_ies:order 27;
		gtp:intsancenum 0;
	}
	container charging_characteristics {
		uses gtp_ies:charging_characteristics;
		gtp_ies:order 28;
		gtp:intsancenum 0;
	}
	container signalling_priority_indication {
		uses gtp_ies:indication;
		gtp_ies:order 33;
		gtp:intsancenum 0;
	}
	container ue_local_ip_address {
		uses gtp_ies:ip_address;
		gtp_ies:order 34;
		gtp:intsancenum 0;
	}
	container ue_udp_port {
		uses gtp_ies:port_number;
		gtp_ies:order 35;
		gtp:intsancenum 0;
	}
	container henb_local_ip_address {
		uses gtp_ies:ip_address;
		gtp_ies:order 37;
		gtp:intsancenum 1;
	}
	container henb_udp_port {
		uses gtp_ies:port_number;
		gtp_ies:order 38;
		gtp:intsancenum 1;
	}
	container mmes4sgsn_identifier {
		uses gtp_ies:ip_address;
		gtp_ies:order 39;
		gtp:intsancenum 2;
	}
	container twan_identifier {
		uses gtp_ies:twan_identifier;
		gtp_ies:order 40;
		gtp:intsancenum 0;
	}
	container epdg_ip_address {
		uses gtp_ies:ip_address;
		gtp_ies:order 41;
		gtp:intsancenum 3;
	}
	container cn_operator_selection_entity {
		uses gtp_ies:cn_operator_selection_entity;
		gtp_ies:order 42;
		gtp:intsancenum 0;
	}
	container presence_reporting_area_information {
		uses gtp_ies:presence_reporting_area_information;
		gtp_ies:order 43;
		gtp:intsancenum 0;
	}
	container mmes4sgsns_overload_control_information {
		uses gtp_ies:overload_control_information;
		gtp_ies:order 44;
		gtp:intsancenum 0;
	}
	container sgws_overload_control_information {
		uses gtp_ies:overload_control_information;
		gtp_ies:order 45;
		gtp:intsancenum 1;
	}
	container twanepdgs_overload_control_information {
		uses gtp_ies:overload_control_information;
		gtp_ies:order 46;
		gtp:intsancenum 2;
	}
	container origination_time_stamp {
		uses gtp_ies:millisecond_time_stamp;
		gtp_ies:order 47;
		gtp:intsancenum 0;
	}
	container maximum_wait_time {
		uses gtp_ies:integer_number;
		gtp_ies:order 48;
		gtp:intsancenum 0;
	}
	container wlan_location_information {
		uses gtp_ies:twan_identifier;
		gtp_ies:order 49;
		gtp:intsancenum 1;
	}
	container wlan_location_timestamp {
		uses gtp_ies:twan_identifier_timestamp;
		gtp_ies:order 50;
		gtp:intsancenum 0;
	}
	container nbifom_container {
		uses gtp_ies:fcontainer;
		gtp_ies:order 51;
		gtp:intsancenum 0;
	}
	container remote_ue_context_connected {
		uses gtp_ies:remote_ue_context;
		gtp_ies:order 52;
		gtp:intsancenum 0;
	}
	container tgpp_aaa_server_identifier {
		uses gtp_ies:node_identifier;
		gtp_ies:order 53;
		gtp:intsancenum 0;
	}
	container extended_protocol_configuration_options {
		uses gtp_ies:epco;
		gtp_ies:order 54;
		gtp:intsancenum 0;
	}
	container serving_plmn_rate_control {
		uses gtp_ies:serving_plmn_rate_control;
		gtp_ies:order 55;
		gtp:intsancenum 0;
	}
	container mo_exception_data_counter {
		uses gtp_ies:counter;
		gtp_ies:order 56;
		gtp:intsancenum 0;
	}
	container ue_tcp_port {
		uses gtp_ies:port_number;
		gtp_ies:order 57;
		gtp:intsancenum 2;
	}
	container mapped_ue_usage_type {
		uses gtp_ies:mapped_ue_usage_type;
		gtp_ies:order 58;
		gtp:intsancenum 0;
	}
	container user_location_information_for_sgw {
		uses gtp_ies:uli;
		gtp_ies:order 59;
		gtp:intsancenum 1;
	}
	container sgwu_node_name {
		uses gtp_ies:fqdn;
		gtp_ies:order 60;
		gtp:intsancenum 0;
	}
	container secondary_rat_usage_data_report {
		uses gtp_ies:secondary_rat_usage_data_report;
		gtp_ies:order 61;
		gtp:intsancenum 0;
	}
	container up_function_selection_indication_flags {
		uses gtp_ies:up_function_selection_indication_flags;
		gtp_ies:order 62;
		gtp:intsancenum 0;
	}
	container private_extension {
		uses gtp_ies:private_extension;
		gtp_ies:order 63;
	}
}
grouping create_session_request__bearer_context_to_be_created {
	gtp_ies:ie-type 93;
	gtp:containingMessage 32;
	container eps_bearer_id {
		uses gtp_ies:ebi;
		gtp_ies:order 1;
		gtp:iemandatory;
		gtp:intsancenum 0;
	}
	container tft {
		uses gtp_ies:bearer_tft;
		gtp_ies:order 2;
		gtp:intsancenum 0;
	}
	container s1u_enodeb_fteid {
		uses gtp_ies:fteid;
		gtp_ies:order 3;
		gtp:intsancenum 0;
	}
	container s4u_sgsn_fteid {
		uses gtp_ies:fteid;
		gtp_ies:order 4;
		gtp:intsancenum 1;
	}
	container s5s8u_sgw_fteid {
		uses gtp_ies:fteid;
		gtp_ies:order 5;
		gtp:intsancenum 2;
	}
	container s5s8u_pgw_fteid {
		uses gtp_ies:fteid;
		gtp_ies:order 6;
		gtp:intsancenum 3;
	}
	container s12_rnc_fteid {
		uses gtp_ies:fteid;
		gtp_ies:order 7;
		gtp:intsancenum 4;
	}
	container s2bu_epdg_fteid {
		uses gtp_ies:fteid;
		gtp_ies:order 8;
		gtp:intsancenum 5;
	}
	container s2au_twan_fteid {
		uses gtp_ies:fteid;
		gtp_ies:order 9;
		gtp:intsancenum 6;
	}
	container bearer_level_qos {
		uses gtp_ies:bearer_qos;
		gtp_ies:order 10;
		gtp:iemandatory;
		gtp:intsancenum 0;
	}
	container s11u_mme_fteid {
		uses gtp_ies:fteid;
		gtp_ies:order 11;
		gtp:intsancenum 7;
	}
}
grouping create_session_request__bearer_context_to_be_removed {
	gtp_ies:ie-type 93;
	gtp:containingMessage 32;
	container eps_bearer_id {
		uses gtp_ies:ebi;
		gtp_ies:order 1;
		gtp:iemandatory;
		gtp:intsancenum 0;
	}
	container s4u_sgsn_fteid {
		uses gtp_ies:fteid;
		gtp_ies:order 2;
		gtp:intsancenum 0;
	}
}
grouping create_session_request__overload_control_information {
	gtp_ies:ie-type 180;
	gtp:containingMessage 32;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping create_session_request__remote_ue_context_connected {
	gtp_ies:ie-type 191;
	gtp:containingMessage 32;
	container remote_user_id {
		uses gtp_ies:remote_user_id;
		gtp_ies:order 1;
		gtp:iemandatory;
		gtp:intsancenum 0;
		description "See subclause 8.123 for the description and use of this parameter
";
	}
	container remote_ue_ip_information {
		uses gtp_ies:remote_ue_ip_information;
		gtp_ies:order 2;
		gtp:iemandatory;
		gtp:intsancenum 0;
		description "See subclause 8.124 for the description and use of this parameter
";
	}
}
grouping create_session_response {
	gtp:messageType "response";
	container cause {
		uses gtp_ies:cause;
		gtp_ies:order 1;
		gtp:iemandatory;
		gtp:intsancenum 0;
	}
	container change_reporting_action {
		uses gtp_ies:change_reporting_action;
		gtp_ies:order 2;
		gtp:intsancenum 0;
	}
	container csg_information_reporting_action {
		uses gtp_ies:csg_information_reporting_action;
		gtp_ies:order 3;
		gtp:intsancenum 0;
	}
	container henb_information_reporting {
		uses gtp_ies:henb_information_reporting;
		gtp_ies:order 4;
		gtp:intsancenum 0;
	}
	container sender_fteid_for_control_plane {
		uses gtp_ies:fteid;
		gtp_ies:order 5;
		gtp:intsancenum 0;
	}
	container pgw_s5s8_s2as2b_fteid_for_pmip_based_interface_or_for_gtp_based_control_plane_interface {
		uses gtp_ies:fteid;
		gtp_ies:order 6;
		gtp:intsancenum 1;
	}
	container pdn_address_allocation {
		uses gtp_ies:paa;
		gtp_ies:order 7;
		gtp:intsancenum 0;
	}
	container apn_restriction {
		uses gtp_ies:apn_restriction;
		gtp_ies:order 8;
		gtp:intsancenum 0;
	}
	container aggregate_maximum_bit_rate {
		uses gtp_ies:ambr;
		gtp_ies:order 9;
		gtp:intsancenum 0;
	}
	container linked_eps_bearer_id {
		uses gtp_ies:ebi;
		gtp_ies:order 10;
		gtp:intsancenum 0;
	}
	container protocol_configuration_options {
		uses gtp_ies:pco;
		gtp_ies:order 11;
		gtp:intsancenum 0;
	}
	container bearer_contexts_created {
		uses gtp_ies:bearer_context;
		gtp_ies:order 12;
		gtp:iemandatory;
		gtp:intsancenum 0;
	}
	container bearer_contexts_marked_for_removal {
		uses gtp_ies:bearer_context;
		gtp_ies:order 13;
		gtp:intsancenum 1;
	}
	container recovery {
		uses gtp_ies:recovery;
		gtp_ies:order 14;
		gtp:intsancenum 0;
	}
	container charging_gateway_name {
		uses gtp_ies:fqdn;
		gtp_ies:order 15;
		gtp:intsancenum 0;
	}
	container charging_gateway_address {
		uses gtp_ies:ip_address;
		gtp_ies:order 16;
		gtp:intsancenum 0;
	}
	container pgwfqcsid {
		uses gtp_ies:fqcsid;
		gtp_ies:order 17;
		gtp:intsancenum 0;
	}
	container sgwfqcsid {
		uses gtp_ies:fqcsid;
		gtp_ies:order 18;
		gtp:intsancenum 1;
	}
	container pgw_backoff_time {
		uses gtp_ies:epc_timer;
		gtp_ies:order 21;
		gtp:intsancenum 0;
	}
	container indication_flags {
		uses gtp_ies:indication;
		gtp_ies:order 24;
		gtp:intsancenum 0;
	}
	container presence_reporting_area_action {
		uses gtp_ies:presence_reporting_area_action;
		gtp_ies:order 25;
		gtp:intsancenum 0;
	}
	container pgws_node_level_load_control_information {
		uses gtp_ies:load_control_information;
		gtp_ies:order 26;
		gtp:intsancenum 0;
	}
	container pgws_apn_level_load_control_information {
		uses gtp_ies:load_control_information;
		gtp_ies:order 27;
		gtp:intsancenum 1;
	}
	container sgws_node_level_load_control_information {
		uses gtp_ies:load_control_information;
		gtp_ies:order 28;
		gtp:intsancenum 2;
	}
	container pgws_overload_control_information {
		uses gtp_ies:overload_control_information;
		gtp_ies:order 29;
		gtp:intsancenum 0;
	}
	container sgws_overload_control_information {
		uses gtp_ies:overload_control_information;
		gtp_ies:order 30;
		gtp:intsancenum 1;
	}
	container nbifom_container {
		uses gtp_ies:fcontainer;
		gtp_ies:order 31;
		gtp:intsancenum 0;
	}
	container pdn_connection_charging_id {
		uses gtp_ies:charging_id;
		gtp_ies:order 32;
		gtp:intsancenum 0;
	}
	container extended_protocol_configuration_options {
		uses gtp_ies:epco;
		gtp_ies:order 33;
		gtp:intsancenum 0;
	}
	container private_extension {
		uses gtp_ies:private_extension;
		gtp_ies:order 34;
	}
}
grouping create_session_response__bearer_context_created {
	gtp_ies:ie-type 93;
	gtp:containingMessage 33;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s1u_sgw_fteid {
		uses gtp_ies:fteid;
		gtp_ies:order 3;
		gtp:intsancenum 0;
	}
	container s4u_sgw_fteid {
		uses gtp_ies:fteid;
		gtp_ies:order 4;
		gtp:intsancenum 1;
	}
	container s5s8u_pgw_fteid {
		uses gtp_ies:fteid;
		gtp_ies:order 5;
		gtp:intsancenum 2;
	}
	container s12_sgw_fteid {
		uses gtp_ies:fteid;
		gtp_ies:order 6;
		gtp:intsancenum 3;
	}
	container s2bu_pgw_fteid {
		uses gtp_ies:fteid;
		gtp_ies:order 7;
		gtp:intsancenum 4;
	}
	container s2au_pgw_fteid {
		uses gtp_ies:fteid;
		gtp_ies:order 8;
		gtp:intsancenum 5;
	}
	container bearer_level_qos {
		uses gtp_ies:bearer_qos;
		gtp_ies:order 9;
		gtp:intsancenum 0;
	}
	container charging_id {
		uses gtp_ies:charging_id;
		gtp_ies:order 10;
		gtp:intsancenum 0;
	}
	container bearer_flags {
		uses gtp_ies:bearer_flags;
		gtp_ies:order 11;
		gtp:intsancenum 0;
	}
	container s11u_sgw_fteid {
		uses gtp_ies:fteid;
		gtp_ies:order 12;
		gtp:intsancenum 6;
	}
}
grouping se__bearer_context_marked_for_removal {
	gtp_ies:ie-type 93;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
		description "This IE shall indicate if the bearer handling was successful, and if not, gives the information on the reason.
";
	}
}
grouping create_session_response__load_control_information {
	gtp_ies:ie-type 181;
	gtp:containingMessage 33;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping create_session_response__overload_control_information {
	gtp_ies:ie-type 180;
	gtp:containingMessage 33;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping create_bearer_request {
	gtp:messageType "request";
	container procedure_transaction_id {
		uses gtp_ies:pti;
		gtp_ies:order 1;
		gtp:intsancenum 0;
	}
	container linked_eps_bearer_id {
		uses gtp_ies:ebi;
		gtp_ies:order 2;
		gtp:iemandatory;
		gtp:intsancenum 0;
	}
	container protocol_configuration_options {
		uses gtp_ies:pco;
		gtp_ies:order 3;
		gtp:intsancenum 0;
	}
	container bearer_contexts {
		uses gtp_ies:bearer_context_;
		gtp_ies:order 4;
		gtp:iemandatory;
		gtp:intsancenum 0;
	}
	container pgwfqcsid {
		uses gtp_ies:fqcsid;
		gtp_ies:order 5;
		gtp:intsancenum 0;
	}
	container sgwfqcsid {
		uses gtp_ies:fqcsid;
		gtp_ies:order 6;
		gtp:intsancenum 1;
	}
	container change_reporting_action {
		uses gtp_ies:change_reporting_action;
		gtp_ies:order 7;
		gtp:intsancenum 0;
	}
	container csg_information_reporting_action {
		uses gtp_ies:csg_information_reporting_action;
		gtp_ies:order 8;
		gtp:intsancenum 0;
	}
	container henb_information_reporting {
		uses gtp_ies:henb_information_reporting;
		gtp_ies:order 9;
		gtp:intsancenum 0;
	}
	container presence_reporting_area_action {
		uses gtp_ies:presence_reporting_area_action;
		gtp_ies:order 10;
		gtp:intsancenum 0;
	}
	container indication_flags {
		uses gtp_ies:indication;
		gtp_ies:order 11;
		gtp:intsancenum 0;
	}
	container pgws_node_level_load_control_information {
		uses gtp_ies:load_control_information;
		gtp_ies:order 12;
		gtp:intsancenum 0;
	}
	container pgws_apn_level_load_control_information {
		uses gtp_ies:load_control_information;
		gtp_ies:order 13;
		gtp:intsancenum 1;
	}
	container sgws_node_level_load_control_information {
		uses gtp_ies:load_control_information;
		gtp_ies:order 14;
		gtp:intsancenum 2;
	}
	container pgws_overload_control_information {
		uses gtp_ies:overload_control_information;
		gtp_ies:order 15;
		gtp:intsancenum 0;
	}
	container sgws_overload_control_information {
		uses gtp_ies:overload_control_information;
		gtp_ies:order 16;
		gtp:intsancenum 1;
	}
	container nbifom_container {
		uses gtp_ies:fcontainer;
		gtp_ies:order 17;
		gtp:intsancenum 0;
	}
	container private_extension {
		uses gtp_ies:private_extension;
		gtp_ies:order 18;
	}
}
grouping create_bearer_request__bearer_context {
	gtp_ies:ie-type 93;
	gtp:containingMessage 95;
	container eps_bearer_id {
		uses gtp_ies:ebi;
		gtp_ies:order 1;
		gtp:iemandatory;
		gtp:intsancenum 0;
	}
	container tft {
		uses gtp_ies:bearer_tft;
		gtp_ies:order 2;
		gtp:iemandatory;
		gtp:intsancenum 0;
	}
	container s1u_sgw_fteid {
		uses gtp_ies:fteid;
		gtp_ies:order 3;
		gtp:intsancenum 0;
	}
	container s58u_pgw_fteid {
		uses gtp_ies:fteid;
		gtp_ies:order 4;
		gtp:intsancenum 1;
	}
	container s12_sgw_fteid {
		uses gtp_ies:fteid;
		gtp_ies:order 5;
		gtp:intsancenum 2;
	}
	container s4u_sgw_fteid {
		uses gtp_ies:fteid;
		gtp_ies:order 6;
		gtp:intsancenum 3;
	}
	container s2bu_pgw_fteid {
		uses gtp_ies:fteid;
		gtp_ies:order 7;
		gtp:intsancenum 4;
	}
	container s2au_pgw_fteid {
		uses gtp_ies:fteid;
		gtp_ies:order 8;
		gtp:intsancenum 5;
	}
	container bearer_level_qos {
		uses gtp_ies:bearer_qos;
		gtp_ies:order 9;
		gtp:iemandatory;
		gtp:intsancenum 0;
	}
	container charging_id {
		uses gtp_ies:charging_id;
		gtp_ies:order 10;
		gtp:intsancenum 0;
	}
	container bearer_flags {
		uses gtp_ies:bearer_flags;
		gtp_ies:order 11;
		gtp:intsancenum 0;
	}
	container protocol_configuration_options {
		uses gtp_ies:pco;
		gtp_ies:order 12;
		gtp:intsancenum 0;
	}
	container extended_protocol_configuration_options {
		uses gtp_ies:epco;
		gtp_ies:order 13;
		gtp:intsancenum 0;
	}
	container maximum_packet_loss_rate {
		uses gtp_ies:maximum_packet_loss_rate;
		gtp_ies:order 14;
		gtp:intsancenum 0;
	}
}
grouping create_bearer_request__load_control_information {
	gtp_ies:ie-type 181;
	gtp:containingMessage 95;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping create_bearer_request__overload_control_information {
	gtp_ies:ie-type 181;
	gtp:containingMessage 95;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping create_bearer_response {
	gtp:messageType "response";
	container cause {
		uses gtp_ies:cause;
		gtp_ies:order 1;
		gtp:iemandatory;
		gtp:intsancenum 0;
	}
	container bearer_contexts {
		uses gtp_ies:bearer_context_;
		gtp_ies:order 2;
		gtp:iemandatory;
		gtp:intsancenum 0;
	}
	container recovery {
		uses gtp_ies:recovery;
		gtp_ies:order 3;
		gtp:intsancenum 0;
	}
	container mmefqcsid {
		uses gtp_ies:fqcsid;
		gtp_ies:order 4;
		gtp:intsancenum 0;
	}
	container sgwfqcsid {
		uses gtp_ies:fqcsid;
		gtp_ies:order 5;
		gtp:intsancenum 1_;
	}
	container epdgfqcsid {
		uses gtp_ies:fqcsid;
		gtp_ies:order 6;
		gtp:intsancenum 2;
	}
	container twanfqcsid {
		uses gtp_ies:fqcsid;
		gtp_ies:order 7;
		gtp:intsancenum 3;
	}
	container protocol_configuration_options {
		uses gtp_ies:pco;
		gtp_ies:order 8;
		gtp:intsancenum 0;
	}
	container ue_time_zone {
		uses gtp_ies:ue_time_zone;
		gtp_ies:order 9;
		gtp:intsancenum 0;
	}
	container user_location_information {
		uses gtp_ies:uli;
		gtp_ies:order 10;
		gtp:intsancenum 0;
	}
	container twan_identifier {
		uses gtp_ies:twan_identifier;
		gtp_ies:order 11;
		gtp:intsancenum 0;
	}
	container mmes4sgsns_overload_control_information {
		uses gtp_ies:overload_control_information;
		gtp_ies:order 12;
		gtp:intsancenum 0;
	}
	container sgws_overload_control_information {
		uses gtp_ies:overload_control_information;
		gtp_ies:order 13;
		gtp:intsancenum 1;
	}
	container presence_reporting_area_information {
		uses gtp_ies:presence_reporting_area_information;
		gtp_ies:order 14;
		gtp:intsancenum 0;
	}
	container mmes4sgsn_identifier {
		uses gtp_ies:ip_address;
		gtp_ies:order 15;
		gtp:intsancenum 0;
	}
	container twanepdgs_overload_control_information {
		uses gtp_ies:overload_control_information;
		gtp_ies:order 16;
		gtp:intsancenum 2;
	}
	container wlan_location_information {
		uses gtp_ies:twan_identifier;
		gtp_ies:order 17;
		gtp:intsancenum 1;
	}
	container wlan_location_timestamp {
		uses gtp_ies:twan_identifier_timestamp;
		gtp_ies:order 18;
		gtp:intsancenum 1;
	}
	container ue_local_ip_address {
		uses gtp_ies:ip_address;
		gtp_ies:order 19;
		gtp:intsancenum 0;
	}
	container ue_udp_port {
		uses gtp_ies:port_number;
		gtp_ies:order 20;
		gtp:intsancenum 0;
	}
	container nbifom_container {
		uses gtp_ies:fcontainer;
		gtp_ies:order 21;
		gtp:intsancenum 0;
	}
	container ue_tcp_port {
		uses gtp_ies:port_number;
		gtp_ies:order 22;
		gtp:intsancenum 1;
	}
	container private_extension {
		uses gtp_ies:private_extension;
		gtp_ies:order 23;
	}
}
grouping create_bearer_response__bearer_context {
	gtp_ies:ie-type 93;
	gtp:containingMessage 96;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s1u_enodeb_fteid {
		uses gtp_ies:fteid;
		gtp_ies:order 3;
		gtp:intsancenum 0;
	}
	container s1u_sgw_fteid {
		uses gtp_ies:fteid;
		gtp_ies:order 4;
		gtp:intsancenum 1;
	}
	container s58u_sgw_fteid {
		uses gtp_ies:fteid;
		gtp_ies:order 5;
		gtp:intsancenum 2;
	}
	container s58u_pgw_fteid {
		uses gtp_ies:fteid;
		gtp_ies:order 6;
		gtp:intsancenum 3;
	}
	container s12_rnc_fteid {
		uses gtp_ies:fteid;
		gtp_ies:order 7;
		gtp:intsancenum 4;
	}
	container s12_sgw_fteid {
		uses gtp_ies:fteid;
		gtp_ies:order 8;
		gtp:intsancenum 5;
	}
	container s4u_sgsn_fteid {
		uses gtp_ies:fteid;
		gtp_ies:order 9;
		gtp:intsancenum 6;
	}
	container s4u_sgw_fteid {
		uses gtp_ies:fteid;
		gtp_ies:order 10;
		gtp:intsancenum 7;
	}
	container s2bu_epdg_fteid {
		uses gtp_ies:fteid;
		gtp_ies:order 11;
		gtp:intsancenum 8;
	}
	container s2bu_pgw_fteid {
		uses gtp_ies:fteid;
		gtp_ies:order 12;
		gtp:intsancenum 9;
	}
	container s2au_twan_fteid {
		uses gtp_ies:fteid;
		gtp_ies:order 13;
		gtp:intsancenum 10;
	}
	container s2au_pgw_fteid {
		uses gtp_ies:fteid;
		gtp_ies:order 14;
		gtp:intsancenum 11;
	}
	container protocol_configuration_options {
		uses gtp_ies:pco;
		gtp_ies:order 15;
		gtp:intsancenum 0;
	}
	container rannas_cause {
		uses gtp_ies:rannas_cause;
		gtp_ies:order 16;
		gtp:intsancenum 0;
	}
	container extended_protocol_configuration_options {
		uses gtp_ies:epco;
		gtp_ies:order 17;
		gtp:intsancenum 0;
	}
}
grouping create_bearer_response__overload_control_information {
	gtp_ies:ie-type 180;
	gtp:containingMessage 96;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping bearer_resource_command_request {
	gtp:messageType "request";
	container linked_eps_bearer_id {
		uses gtp_ies:ebi;
		gtp_ies:order 1;
		gtp:iemandatory;
		gtp:intsancenum 0;
	}
	container procedure_transaction_id {
		uses gtp_ies:pti;
		gtp_ies:order 2;
		gtp:iemandatory;
		gtp:intsancenum 0;
	}
	container flow_quality_of_service {
		uses gtp_ies:flow_qos;
		gtp_ies:order 3;
		gtp:intsancenum 0;
	}
	container traffic_aggregate_description {
		uses gtp_ies:tad;
		gtp_ies:order 4;
		gtp:intsancenum 0;
	}
	container rat_type {
		uses gtp_ies:rat_type;
		gtp_ies:order 5;
		gtp:intsancenum 0;
	}
	container serving_network {
		uses gtp_ies:serving_network;
		gtp_ies:order 6;
		gtp:intsancenum 0;
	}
	container user_location_information {
		uses gtp_ies:uli;
		gtp_ies:order 7;
		gtp:intsancenum 0;
	}
	container eps_bearer_id {
		uses gtp_ies:ebi;
		gtp_ies:order 8;
		gtp:intsancenum 1;
	}
	container indication_flags {
		uses gtp_ies:indication;
		gtp_ies:order 9;
		gtp:intsancenum 0;
	}
	container s4u_sgsn_fteid {
		uses gtp_ies:fteid;
		gtp_ies:order 10;
		gtp:intsancenum 0;
	}
	container s12_rnc_fteid {
		uses gtp_ies:fteid;
		gtp_ies:order 11;
		gtp:intsancenum 1;
	}
	container protocol_configuration_options {
		uses gtp_ies:pco;
		gtp_ies:order 12;
		gtp:intsancenum 0;
	}
	container signalling_priority_indication {
		uses gtp_ies:signalling_priority_indication;
		gtp_ies:order 13;
		gtp:intsancenum 0;
	}
	container mmes4sgsns_overload_control_information {
		uses gtp_ies:overload_control_information;
		gtp_ies:order 14;
		gtp:intsancenum 0;
	}
	container sgws_overload_control_information {
		uses gtp_ies:overload_control_information;
		gtp_ies:order 15;
		gtp:intsancenum 1;
	}
	container nbifom_container {
		uses gtp_ies:fcontainer;
		gtp_ies:order 16;
		gtp:intsancenum 0;
	}
	container extended_protocol_configuration_options {
		uses gtp_ies:epco;
		gtp_ies:order 17;
		gtp:intsancenum 0;
	}
	container sender_fteid_for_control_plane {
		uses gtp_ies:fteid;
		gtp_ies:order 18;
		gtp:intsancenum 2;
	}
	container private_extension {
		uses gtp_ies:private_extension;
		gtp_ies:order 19;
	}
}
grouping bearer_resource_command__overload_control_information {
	gtp_ies:ie-type 180;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping bearer_resource_failure_indication_request {
	gtp:messageType "request";
	container cause {
		uses gtp_ies:cause;
		gtp_ies:order 1;
		gtp:iemandatory;
		gtp:intsancenum 0;
	}
	container linked_eps_bearer_id {
		uses gtp_ies:ebi;
		gtp_ies:order 2;
		gtp:iemandatory;
		gtp:intsancenum 0;
	}
	container procedure_transaction_id {
		uses gtp_ies:pti;
		gtp_ies:order 3;
		gtp:iemandatory;
		gtp:intsancenum 0;
	}
	container indication_flags {
		uses gtp_ies:indication;
		gtp_ies:order 4;
		gtp:intsancenum 0;
	}
	container pgws_overload_control_information {
		uses gtp_ies:overload_control_information;
		gtp_ies:order 5;
		gtp:intsancenum 0;
	}
	container sgws_overload_control_information {
		uses gtp_ies:overload_control_information;
		gtp_ies:order 6;
		gtp:intsancenum 1;
	}
	container recovery {
		uses gtp_ies:recovery;
		gtp_ies:order 7;
		gtp:intsancenum 0;
	}
	container nbifom_container {
		uses gtp_ies:fcontainer;
		gtp_ies:order 8;
		gtp:intsancenum 0;
	}
	container private_extension {
		uses gtp_ies:private_extension;
		gtp_ies:order 9;
	}
}
grouping bearer_resource_failure_indication__overload_control_information {
	gtp_ies:ie-type 180;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping modify_bearer_request {
	gtp:messageType "request";
	container me_identity {
		uses gtp_ies:mei;
		gtp_ies:order 1;
		gtp:intsancenum 0;
	}
	container user_location_information {
		uses gtp_ies:uli;
		gtp_ies:order 2;
		gtp:intsancenum 0;
	}
	container serving_network {
		uses gtp_ies:serving_network;
		gtp_ies:order 3;
		gtp:intsancenum 0;
	}
	container indication_flags {
		uses gtp_ies:indication;
		gtp_ies:order 4;
		gtp:intsancenum 0;
	}
	container sender_fteid_for_control_plane {
		uses gtp_ies:fteid;
		gtp_ies:order 5;
		gtp:intsancenum 0;
	}
	container aggregate_maximum_bit_rate {
		uses gtp_ies:ambr;
		gtp_ies:order 6;
		gtp:intsancenum 0;
	}
	container delay_downlink_packet_notification_request {
		uses gtp_ies:delay_value;
		gtp_ies:order 7;
		gtp:intsancenum 0;
	}
	container bearer_contexts_to_be_modified {
		uses gtp_ies:bearer_context;
		gtp_ies:order 8;
		gtp:intsancenum 0;
	}
	container bearer_contexts_to_be_removed {
		uses gtp_ies:bearer_context;
		gtp_ies:order 9;
		gtp:intsancenum 1;
	}
	container recovery {
		uses gtp_ies:recovery;
		gtp_ies:order 10;
		gtp:intsancenum 0;
	}
	container ue_time_zone {
		uses gtp_ies:ue_time_zone;
		gtp_ies:order 11;
		gtp:intsancenum 0;
	}
	container mmefqcsid {
		uses gtp_ies:fqcsid;
		gtp_ies:order 12;
		gtp:intsancenum 0;
	}
	container sgwfqcsid {
		uses gtp_ies:fqcsid;
		gtp_ies:order 13;
		gtp:intsancenum 1_;
	}
	container user_csg_information {
		uses gtp_ies:uci;
		gtp_ies:order 14;
		gtp:intsancenum 0;
	}
	container ue_local_ip_address {
		uses gtp_ies:ip_address;
		gtp_ies:order 15;
		gtp:intsancenum 1;
	}
	container ue_udp_port {
		uses gtp_ies:port_number;
		gtp_ies:order 16;
		gtp:intsancenum 1;
	}
	container henb_local_ip_address {
		uses gtp_ies:ip_address;
		gtp_ies:order 19;
		gtp:intsancenum 0;
	}
	container henb_udp_port {
		uses gtp_ies:port_number;
		gtp_ies:order 20;
		gtp:intsancenum 0;
	}
	container mmes4sgsn_identifier {
		uses gtp_ies:ip_address;
		gtp_ies:order 21;
		gtp:intsancenum 2;
	}
	container cn_operator_selection_entity {
		uses gtp_ies:cn_operator_selection_entity;
		gtp_ies:order 22;
		gtp:intsancenum 0;
	}
	container presence_reporting_area_information {
		uses gtp_ies:presence_reporting_area_information;
		gtp_ies:order 23;
		gtp:intsancenum 0;
	}
	container mmes4sgsns_overload_control_information {
		uses gtp_ies:overload_control_information;
		gtp_ies:order 24;
		gtp:intsancenum 0;
	}
	container sgws_overload_control_information {
		uses gtp_ies:overload_control_information;
		gtp_ies:order 25;
		gtp:intsancenum 1;
	}
	container epdgs_overload_control_information {
		uses gtp_ies:overload_control_information;
		gtp_ies:order 26;
		gtp:intsancenum 2;
	}
	container serving_plmn_rate_control {
		uses gtp_ies:serving_plmn_rate_control;
		gtp_ies:order 27;
		gtp:intsancenum 0;
	}
	container mo_exception_data_counter {
		uses gtp_ies:counter;
		gtp_ies:order 28;
		gtp:intsancenum 0;
	}
	container imsi {
		uses gtp_ies:imsi;
		gtp_ies:order 29;
		gtp:intsancenum 0;
	}
	container user_location_information_for_sgw {
		uses gtp_ies:uli;
		gtp_ies:order 30;
		gtp:intsancenum 1;
	}
	container wlan_location_information {
		uses gtp_ies:twan_identifier;
		gtp_ies:order 31;
		gtp:intsancenum 0;
	}
	container wlan_location_timestamp {
		uses gtp_ies:twan_identifier_timestamp;
		gtp_ies:order 32;
		gtp:intsancenum 0;
	}
	container secondary_rat_usage_data_report {
		uses gtp_ies:secondary_rat_usage_data_report;
		gtp_ies:order 33;
		gtp:intsancenum 0;
	}
	container private_extension {
		uses gtp_ies:private_extension;
		gtp_ies:order 34;
	}
}
grouping modify_bearer_request__bearer_context_to_be_modified {
	gtp_ies:ie-type 93;
	gtp:containingMessage 34;
	container eps_bearer_id {
		uses gtp_ies:ebi;
		gtp_ies:order 1;
		gtp:iemandatory;
		gtp:intsancenum 0;
	}
	container s1_enodeb_fteid {
		uses gtp_ies:fteid;
		gtp_ies:order 2;
		gtp:intsancenum 0;
	}
	container s58u_sgw_fteid {
		uses gtp_ies:fteid;
		gtp_ies:order 3;
		gtp:intsancenum 1;
	}
	container s12_rnc_fteid {
		uses gtp_ies:fteid;
		gtp_ies:order 4;
		gtp:intsancenum 2;
	}
	container s4u_sgsn_fteid {
		uses gtp_ies:fteid;
		gtp_ies:order 5;
		gtp:intsancenum 3;
	}
	container s11u_mme_fteid {
		uses gtp_ies:fteid;
		gtp_ies:order 6;
		gtp:intsancenum 4;
	}
}
grouping modify_bearer_request__bearer_context_to_be_removed {
	gtp_ies:ie-type 93;
	gtp:containingMessage 34;
	container eps_bearer_id {
		uses gtp_ies:ebi;
		gtp_ies:order 1;
		gtp:iemandatory;
		gtp:intsancenum 0;
	}
}
grouping modify_bearer_request__overload_control_information {
	gtp_ies:ie-type 180;
	gtp:containingMessage 34;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping modify_bearer_response {
	gtp:messageType "response";
	container cause {
		uses gtp_ies:cause;
		gtp_ies:order 1;
		gtp:iemandatory;
		gtp:intsancenum 0;
	}
	container msisdn {
		uses gtp_ies:msisdn;
		gtp_ies:order 2;
		gtp:intsancenum 0;
	}
	container linked_eps_bearer_id {
		uses gtp_ies:ebi;
		gtp_ies:order 3;
		gtp:intsancenum 0;
	}
	container apn_restriction {
		uses gtp_ies:apn_restriction;
		gtp_ies:order 4;
		gtp:intsancenum 0;
	}
	container protocol_configuration_options {
		uses gtp_ies:pco;
		gtp_ies:order 5;
		gtp:intsancenum 0;
	}
	container bearer_contexts_modified {
		uses gtp_ies:bearer_context;
		gtp_ies:order 6;
		gtp:intsancenum 0;
	}
	container bearer_contexts_marked_for_removal {
		uses gtp_ies:bearer_context;
		gtp_ies:order 7;
		gtp:intsancenum 1;
	}
	container change_reporting_action {
		uses gtp_ies:change_reporting_action;
		gtp_ies:order 8;
		gtp:intsancenum 0;
	}
	container csg_information_reporting_action {
		uses gtp_ies:csg_information_reporting_action;
		gtp_ies:order 9;
		gtp:intsancenum 0;
	}
	container henb_information_reporting {
		uses gtp_ies:henb_information_reporting;
		gtp_ies:order 10;
		gtp:intsancenum 0;
	}
	container charging_gateway_name {
		uses gtp_ies:fqdn;
		gtp_ies:order 11;
		gtp:intsancenum 0;
	}
	container charging_gateway_address {
		uses gtp_ies:ip_address;
		gtp_ies:order 12;
		gtp:intsancenum 0;
	}
	container pgwfqcsid {
		uses gtp_ies:fqcsid;
		gtp_ies:order 13;
		gtp:intsancenum 0;
	}
	container sgwfqcsid {
		uses gtp_ies:fqcsid;
		gtp_ies:order 14;
		gtp:intsancenum 1;
	}
	container recovery {
		uses gtp_ies:recovery;
		gtp_ies:order 15;
		gtp:intsancenum 0;
	}
	container indication_flags {
		uses gtp_ies:indication;
		gtp_ies:order 18;
		gtp:intsancenum 0;
	}
	container presence_reporting_area_action {
		uses gtp_ies:presence_reporting_area_action;
		gtp_ies:order 19;
		gtp:intsancenum 0;
	}
	container pgws_node_level_load_control_information {
		uses gtp_ies:load_control_information;
		gtp_ies:order 20;
		gtp:intsancenum 0;
	}
	container pgws_apn_level_load_control_information {
		uses gtp_ies:load_control_information;
		gtp_ies:order 21;
		gtp:intsancenum 1;
	}
	container sgws_node_level_load_control_information {
		uses gtp_ies:load_control_information;
		gtp_ies:order 22;
		gtp:intsancenum 2;
	}
	container pgws_overload_control_information {
		uses gtp_ies:overload_control_information;
		gtp_ies:order 23;
		gtp:intsancenum 0;
	}
	container sgws_overload_control_information {
		uses gtp_ies:overload_control_information;
		gtp_ies:order 24;
		gtp:intsancenum 1;
	}
	container pdn_connection_charging_id {
		uses gtp_ies:charging_id;
		gtp_ies:order 25;
		gtp:intsancenum 0;
	}
	container private_extension {
		uses gtp_ies:private_extension;
		gtp_ies:order 26;
	}
}
grouping modify_bearer_response__bearer_context_modified {
	gtp_ies:ie-type 93;
	gtp:containingMessage 35;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s1u_sgw_fteid {
		uses gtp_ies:fteid;
		gtp_ies:order 3;
		gtp:intsancenum 0;
	}
	container s12_sgw_fteid {
		uses gtp_ies:fteid;
		gtp_ies:order 4;
		gtp:intsancenum 1;
	}
	container s4u_sgw_fteid {
		uses gtp_ies:fteid;
		gtp_ies:order 5;
		gtp:intsancenum 2;
	}
	container charging_id {
		uses gtp_ies:charging_id;
		gtp_ies:order 6;
		gtp:intsancenum 0;
	}
	container bearer_flags {
		uses gtp_ies:bearer_flags;
		gtp_ies:order 7;
		gtp:intsancenum 0;
	}
	container s11u_sgw_fteid {
		uses gtp_ies:fteid;
		gtp_ies:order 8;
		gtp:intsancenum 3;
	}
}
grouping modify_bearer_response__bearer_context_marked_for_removal {
	gtp_ies:ie-type 93;
	gtp:containingMessage 35;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
		description "This IE shall indicate if the bearer handling was successful, and if not, gives information on the reason.
";
	}
}
grouping modify_bearer_response__load_control_information {
	gtp_ies:ie-type 181;
	gtp:containingMessage 35;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping modify_bearer_response__overload_control_information {
	gtp_ies:ie-type 180;
	gtp:containingMessage 35;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping delete_session_request {
	gtp:messageType "request";
	container linked_eps_bearer_id {
		uses gtp_ies:ebi;
		gtp_ies:order 1;
		gtp:intsancenum 0;
	}
	container user_location_information {
		uses gtp_ies:uli;
		gtp_ies:order 2;
		gtp:intsancenum 0;
	}
	container indication_flags {
		uses gtp_ies:indication;
		gtp_ies:order 3;
		gtp:intsancenum 0;
	}
	container protocol_configuration_options {
		uses gtp_ies:pco;
		gtp_ies:order 4;
		gtp:intsancenum 0;
	}
	container originating_node {
		uses gtp_ies:node_type;
		gtp_ies:order 5;
		gtp:intsancenum 0;
	}
	container sender_fteid_for_control_plane {
		uses gtp_ies:fteid;
		gtp_ies:order 6;
		gtp:intsancenum 0;
	}
	container ue_time_zone {
		uses gtp_ies:ue_time_zone;
		gtp_ies:order 7;
		gtp:intsancenum 0;
	}
	container uli_timestamp {
		uses gtp_ies:uli_timestamp;
		gtp_ies:order 8;
		gtp:intsancenum 0;
	}
	container rannas_release_cause {
		uses gtp_ies:rannas_cause;
		gtp_ies:order 9;
		gtp:intsancenum 0;
	}
	container twan_identifier {
		uses gtp_ies:twan_identifier;
		gtp_ies:order 10;
		gtp:intsancenum 0;
	}
	container twan_identifier_timestamp {
		uses gtp_ies:twan_identifier_timestamp;
		gtp_ies:order 11;
		gtp:intsancenum 0;
	}
	container mmes4sgsns_overload_control_information {
		uses gtp_ies:overload_control_information;
		gtp_ies:order 12;
		gtp:intsancenum 0;
	}
	container sgws_overload_control_information {
		uses gtp_ies:overload_control_information;
		gtp_ies:order 13;
		gtp:intsancenum 1;
	}
	container twanepdgs_overload_control_information {
		uses gtp_ies:overload_control_information;
		gtp_ies:order 14;
		gtp:intsancenum 2;
	}
	container wlan_location_information {
		uses gtp_ies:twan_identifier;
		gtp_ies:order 15;
		gtp:intsancenum 1;
	}
	container wlan_location_timestamp {
		uses gtp_ies:twan_identifier_timestamp;
		gtp_ies:order 16;
		gtp:intsancenum 1;
	}
	container ue_local_ip_address {
		uses gtp_ies:ip_address;
		gtp_ies:order 17;
		gtp:intsancenum 0;
	}
	container ue_udp_port {
		uses gtp_ies:port_number;
		gtp_ies:order 18;
		gtp:intsancenum 0;
	}
	container extended_protocol_configuration_options {
		uses gtp_ies:epco;
		gtp_ies:order 19;
		gtp:intsancenum 0;
	}
	container ue_tcp_port {
		uses gtp_ies:port_number;
		gtp_ies:order 20;
		gtp:intsancenum 1;
	}
	container secondary_rat_usage_data_report {
		uses gtp_ies:secondary_rat_usage_data_report;
		gtp_ies:order 21;
		gtp:intsancenum 0;
	}
	container private_extension {
		uses gtp_ies:private_extension;
		gtp_ies:order 22;
	}
}
grouping delete_session_request__overload_control_information {
	gtp_ies:ie-type 180;
	gtp:containingMessage 36;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping delete_bearer_request {
	gtp:messageType "request";
	container eps_bearer_ids {
		uses gtp_ies:ebi;
		gtp_ies:order 1;
		gtp:intsancenum 1;
	}
	container failed_bearer_contexts {
		uses gtp_ies:bearer_context;
		gtp_ies:order 2;
		gtp:intsancenum 0;
	}
	container procedure_transaction_id {
		uses gtp_ies:pti;
		gtp_ies:order 3;
		gtp:intsancenum 0;
	}
	container protocol_configuration_options {
		uses gtp_ies:pco;
		gtp_ies:order 4;
		gtp:intsancenum 0;
	}
	container pgwfqcsid {
		uses gtp_ies:fqcsid;
		gtp_ies:order 5;
		gtp:intsancenum 0;
	}
	container sgwfqcsid {
		uses gtp_ies:fqcsid;
		gtp_ies:order 6;
		gtp:intsancenum 1;
	}
	container indication_flags {
		uses gtp_ies:indication;
		gtp_ies:order 7;
		gtp:intsancenum 0;
	}
	container pgws_node_level_load_control_information {
		uses gtp_ies:load_control_information;
		gtp_ies:order 8;
		gtp:intsancenum 0;
	}
	container pgws_apn_level_load_control_information {
		uses gtp_ies:load_control_information;
		gtp_ies:order 9;
		gtp:intsancenum 1;
	}
	container sgws_node_level_load_control_information {
		uses gtp_ies:load_control_information;
		gtp_ies:order 10;
		gtp:intsancenum 2;
	}
	container pgws_overload_control_information {
		uses gtp_ies:overload_control_information;
		gtp_ies:order 11;
		gtp:intsancenum 0;
	}
	container sgws_overload_control_information {
		uses gtp_ies:overload_control_information;
		gtp_ies:order 12;
		gtp:intsancenum 1;
	}
	container nbifom_container {
		uses gtp_ies:fcontainer;
		gtp_ies:order 13;
		gtp:intsancenum 0;
	}
	container extended_protocol_configuration_options {
		uses gtp_ies:epco;
		gtp_ies:order 14;
		gtp:intsancenum 0;
	}
	container private_extension {
		uses gtp_ies:private_extension;
		gtp_ies:order 15;
	}
}
grouping delete_bearer_request__bearer_context {
	gtp_ies:ie-type 93;
	gtp:containingMessage 99;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
		description "This IE shall indicate the reason of the unsuccessful handling of the bearer.
";
	}
}
grouping delete_bearer_request__load_control_information {
	gtp_ies:ie-type 181;
	gtp:containingMessage 99;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping delete_bearer_request__overload_control_information {
	gtp_ies:ie-type 180;
	gtp:containingMessage 99;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping delete_session_response {
	gtp:messageType "response";
	container cause {
		uses gtp_ies:cause;
		gtp_ies:order 1;
		gtp:iemandatory;
		gtp:intsancenum 0;
	}
	container recovery {
		uses gtp_ies:recovery;
		gtp_ies:order 2;
		gtp:intsancenum 0;
	}
	container protocol_configuration_options {
		uses gtp_ies:pco;
		gtp_ies:order 3;
		gtp:intsancenum 0;
	}
	container indication_flags {
		uses gtp_ies:indication;
		gtp_ies:order 4;
		gtp:intsancenum 0;
	}
	container pgws_node_level_load_control_information {
		uses gtp_ies:load_control_information;
		gtp_ies:order 5;
		gtp:intsancenum 0;
	}
	container pgws_apn_level_load_control_information {
		uses gtp_ies:load_control_information;
		gtp_ies:order 6;
		gtp:intsancenum 1;
	}
	container sgws_node_level_load_control_information {
		uses gtp_ies:load_control_information;
		gtp_ies:order 7;
		gtp:intsancenum 2;
	}
	container pgws_overload_control_information {
		uses gtp_ies:overload_control_information;
		gtp_ies:order 8;
		gtp:intsancenum 0;
	}
	container sgws_overload_control_information {
		uses gtp_ies:overload_control_information;
		gtp_ies:order 9;
		gtp:intsancenum 1;
	}
	container extended_protocol_configuration_options {
		uses gtp_ies:epco;
		gtp_ies:order 10;
		gtp:intsancenum 0;
	}
	container private_extension {
		uses gtp_ies:private_extension;
		gtp_ies:order 11;
	}
}
grouping delete_session_response__load_control_information {
	gtp_ies:ie-type 181;
	gtp:containingMessage 37;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping delete_session_response__overload_control_information {
	gtp_ies:ie-type 180;
	gtp:containingMessage 37;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping delete_bearer_response {
	gtp:messageType "response";
	gtp:messageTypeValue 100;
	container cause {
		uses gtp_ies:cause;
		gtp_ies:order 1;
		gtp:iemandatory;
		gtp:intsancenum 0;
	}
	container linked_eps_bearer_id {
		uses gtp_ies:ebi;
		gtp_ies:order 2;
		gtp:intsancenum 0;
	}
	container bearer_contexts {
		uses gtp_ies:bearer_context_;
		gtp_ies:order 3;
		gtp:intsancenum 0;
	}
	container recovery {
		uses gtp_ies:recovery;
		gtp_ies:order 4;
		gtp:intsancenum 0;
	}
	container mmefqcsid {
		uses gtp_ies:fqcsid;
		gtp_ies:order 5;
		gtp:intsancenum 0;
	}
	container sgwfqcsid {
		uses gtp_ies:fqcsid;
		gtp_ies:order 6;
		gtp:intsancenum 1;
	}
	container epdgfqcsid {
		uses gtp_ies:fqcsid;
		gtp_ies:order 7;
		gtp:intsancenum 2;
	}
	container twanfqcsid {
		uses gtp_ies:fqcsid;
		gtp_ies:order 8;
		gtp:intsancenum 3;
	}
	container protocol_configuration_options {
		uses gtp_ies:pco;
		gtp_ies:order 9;
		gtp:intsancenum 0;
	}
	container ue_time_zone {
		uses gtp_ies:ue_time_zone;
		gtp_ies:order 10;
		gtp:intsancenum 0;
	}
	container user_location_information {
		uses gtp_ies:uli;
		gtp_ies:order 11;
		gtp:intsancenum 0;
	}
	container uli_timestamp {
		uses gtp_ies:uli_timestamp;
		gtp_ies:order 12;
		gtp:intsancenum 0;
	}
	container twan_identifier {
		uses gtp_ies:twan_identifier;
		gtp_ies:order 13;
		gtp:intsancenum 0;
	}
	container twan_identifier_timestamp {
		uses gtp_ies:twan_identifier_timestamp;
		gtp_ies:order 14;
		gtp:intsancenum 0;
	}
	container mmes4sgsns_overload_control_information {
		uses gtp_ies:overload_control_information;
		gtp_ies:order 15;
		gtp:intsancenum 0;
	}
	container sgws_overload_control_information {
		uses gtp_ies:overload_control_information;
		gtp_ies:order 16;
		gtp:intsancenum 1;
	}
	container mmes4sgsn_identifier {
		uses gtp_ies:ip_address;
		gtp_ies:order 17;
		gtp:intsancenum 0;
	}
	container twanepdgs_overload_control_information {
		uses gtp_ies:overload_control_information;
		gtp_ies:order 18;
		gtp:intsancenum 2;
	}
	container wlan_location_information {
		uses gtp_ies:twan_identifier;
		gtp_ies:order 19;
		gtp:intsancenum 1;
	}
	container wlan_location_timestamp {
		uses gtp_ies:twan_identifier_timestamp;
		gtp_ies:order 20;
		gtp:intsancenum 1;
	}
	container ue_local_ip_address {
		uses gtp_ies:ip_address;
		gtp_ies:order 21;
		gtp:intsancenum 0;
	}
	container ue_udp_port {
		uses gtp_ies:port_number;
		gtp_ies:order 22;
		gtp:intsancenum 0;
	}
	container nbifom_container {
		uses gtp_ies:fcontainer;
		gtp_ies:order 23;
		gtp:intsancenum 0;
	}
	container ue_tcp_port {
		uses gtp_ies:port_number;
		gtp_ies:order 24;
		gtp:intsancenum 1;
	}
	container secondary_rat_usage_data_report {
		uses gtp_ies:secondary_rat_usage_data_report;
		gtp_ies:order 25;
		gtp:intsancenum 0;
	}
	container private_extension {
		uses gtp_ies:private_extension;
		gtp_ies:order 26;
	}
}
grouping delete_bearer_response__bearer_context {
	gtp_ies:ie-type 93;
	gtp:containingMessage 100;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container protocol_configuration_options {
		uses gtp_ies:pco;
		gtp_ies:order 3;
		gtp:intsancenum 0;
	}
	container rannas_cause {
		uses gtp_ies:rannas_cause;
		gtp_ies:order 4;
		gtp:intsancenum 0;
	}
	container extended_protocol_configuration_options {
		uses gtp_ies:epco;
		gtp_ies:order 5;
		gtp:intsancenum 0;
	}
}
grouping delete_bearer_response__overload_control_information {
	gtp_ies:ie-type 180;
	gtp:containingMessage 100;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping downlink_data_notification_request {
	gtp:messageType "request";
	container cause {
		uses gtp_ies:cause;
		gtp_ies:order 1;
		gtp:intsancenum 0;
	}
	container eps_bearer_id {
		uses gtp_ies:ebi;
		gtp_ies:order 2;
		gtp:intsancenum 0;
	}
	container allocationretention_priority {
		uses gtp_ies:arp;
		gtp_ies:order 3;
		gtp:intsancenum 0;
	}
	container imsi {
		uses gtp_ies:imsi;
		gtp_ies:order 4;
		gtp:intsancenum 0;
	}
	container sender_fteid_for_control_plane {
		uses gtp_ies:fteid;
		gtp_ies:order 5;
		gtp:intsancenum 0;
	}
	container indication_flags {
		uses gtp_ies:indication;
		gtp_ies:order 6;
		gtp:intsancenum 0;
	}
	container sgws_node_level_load_control_information {
		uses gtp_ies:load_control_information;
		gtp_ies:order 7;
		gtp:intsancenum 0;
	}
	container sgws_overload_control_information {
		uses gtp_ies:overload_control_information;
		gtp_ies:order 8;
		gtp:intsancenum 0;
	}
	container paging_and_service_information {
		uses gtp_ies:paging_and_service_information;
		gtp_ies:order 9;
		gtp:intsancenum 0;
	}
	container private_extension {
		uses gtp_ies:private_extension;
		gtp_ies:order 10;
	}
}
grouping downlink_data_notification__load_control_information {
	gtp_ies:ie-type 181;
	gtp:containingMessage 176;
	container load_control_sequence_number {
		uses gtp_ies:sequence_number;
		gtp_ies:order 1;
		gtp:iemandatory;
		gtp:intsancenum 0;
		description "See clause 12.2.5.1.2.1 for the description and use of this parameter.
";
	}
	container load_metric {
		uses gtp_ies:metric;
		gtp_ies:order 2;
		gtp:iemandatory;
		gtp:intsancenum 0;
		description "See clause 12.2.5.1.2.2 for the description and use of this parameter.
";
	}
}
grouping downlink_data_notification__overload_control_information {
	gtp_ies:ie-type 180;
	gtp:containingMessage 176;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping downlink_data_notification_acknowledge_response {
	gtp:messageType "response";
	container cause {
		uses gtp_ies:cause;
		gtp_ies:order 1;
		gtp:iemandatory;
		gtp:intsancenum 0;
	}
	container data_notification_delay {
		uses gtp_ies:delay_value;
		gtp_ies:order 2;
		gtp:intsancenum 0;
	}
	container recovery {
		uses gtp_ies:recovery;
		gtp_ies:order 3;
		gtp:intsancenum 0;
	}
	container dl_low_priority_traffic_throttling {
		uses gtp_ies:throttling;
		gtp_ies:order 4;
		gtp:intsancenum 0;
	}
	container imsi {
		uses gtp_ies:imsi;
		gtp_ies:order 5;
		gtp:intsancenum 0;
	}
	container dl_buffering_duration {
		uses gtp_ies:epc_timer;
		gtp_ies:order 6;
		gtp:intsancenum 0;
	}
	container dl_buffering_suggested_packet_count {
		uses gtp_ies:integer_number;
		gtp_ies:order 7;
		gtp:intsancenum 0;
	}
	container private_extension {
		uses gtp_ies:private_extension;
		gtp_ies:order 8;
	}
}
grouping downlink_data_notification_failure_indication {
	gtp:messageType "indication";
	container cause {
		uses gtp_ies:cause;
		gtp_ies:order 1;
		gtp:iemandatory;
		gtp:intsancenum 0;
	}
	container originating_node {
		uses gtp_ies:node_type;
		gtp_ies:order 2;
		gtp:intsancenum 0;
		description "This IE shall be included on the S4/S11 interface if the ISR associated GTP entities i.e. MME, S4-SGSN, send this message to the SGW during the Network Triggered Service Request procedure to denote the type of the node originating the message.
";
	}
	container imsi {
		uses gtp_ies:imsi;
		gtp_ies:order 3;
		gtp:intsancenum 0;
		description "3GPP TS 23.007 [17] specifies conditions for sending this IE on the S11/S4 interface as part of the network triggered service restoration procedure, if both the SGW and the MME/S4-SGSN support this optional feature.
";
	}
	container private_extension {
		uses gtp_ies:private_extension;
		gtp_ies:order 4;
	}
}
grouping modify_bearer_command {
	gtp:messageType "command";
	container apnaggregate_maximum_bit_rate {
		uses gtp_ies:ambr;
		gtp_ies:order 1;
		gtp:iemandatory;
		gtp:intsancenum 0;
	}
	container bearer_context {
		uses gtp_ies:bearer_context_;
		gtp_ies:order 2;
		gtp:iemandatory;
		gtp:intsancenum 0;
	}
	container mmes4sgsns_overload_control_information {
		uses gtp_ies:overload_control_information;
		gtp_ies:order 3;
		gtp:intsancenum 0;
	}
	container sgws_overload_control_information {
		uses gtp_ies:overload_control_information;
		gtp_ies:order 4;
		gtp:intsancenum 1;
	}
	container twanepdgs_overload_control_information {
		uses gtp_ies:overload_control_information;
		gtp_ies:order 5;
		gtp:intsancenum 2;
	}
	container sender_fteid_for_control_plane {
		uses gtp_ies:fteid;
		gtp_ies:order 6;
		gtp:intsancenum 0;
	}
	container private_extension {
		uses gtp_ies:private_extension;
		gtp_ies:order 7;
	}
}
grouping modify_bearer_command__bearer_context {
	gtp_ies:ie-type 93;
	container eps_bearer_id {
		uses gtp_ies:ebi;
		gtp_ies:order 1;
		gtp:iemandatory;
		gtp:intsancenum 0;
	}
	container bearer_level_qos {
		uses gtp_ies:bearer_qos;
		gtp_ies:order 2;
		gtp:intsancenum 0;
	}
}
grouping modify_bearer_command__overload_control_information {
	gtp_ies:ie-type 181;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping modify_bearer_failure_indication {
	gtp:messageType "request";
	container cause {
		uses gtp_ies:cause;
		gtp_ies:order 1;
		gtp:iemandatory;
		gtp:intsancenum 0;
	}
	container recovery {
		uses gtp_ies:recovery;
		gtp_ies:order 2;
		gtp:intsancenum 0;
	}
	container indication_flags {
		uses gtp_ies:indication;
		gtp_ies:order 3;
		gtp:intsancenum 0;
	}
	container pgws_overload_control_information {
		uses gtp_ies:overload_control_information;
		gtp_ies:order 4;
		gtp:intsancenum 0;
	}
	container sgws_overload_control_information {
		uses gtp_ies:overload_control_information;
		gtp_ies:order 5;
		gtp:intsancenum 1;
	}
	container private_extension {
		uses gtp_ies:private_extension;
		gtp_ies:order 6;
	}
}
grouping modify_bearer_failure_indication__overload_control_information {
	gtp_ies:ie-type 180;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping update_bearer_request {
	gtp:messageType "request";
	container bearer_contexts {
		uses gtp_ies:bearer_context_;
		gtp_ies:order 1;
		gtp:iemandatory;
		gtp:intsancenum 0;
	}
	container procedure_transaction_id {
		uses gtp_ies:pti;
		gtp_ies:order 2;
		gtp:intsancenum 0;
	}
	container protocol_configuration_options {
		uses gtp_ies:pco;
		gtp_ies:order 3;
		gtp:intsancenum 0;
	}
	container aggregate_maximum_bit_rate {
		uses gtp_ies:ambr;
		gtp_ies:order 4;
		gtp:iemandatory;
		gtp:intsancenum 0;
	}
	container change_reporting_action {
		uses gtp_ies:change_reporting_action;
		gtp_ies:order 5;
		gtp:intsancenum 0;
	}
	container csg_information_reporting_action {
		uses gtp_ies:csg_information_reporting_action;
		gtp_ies:order 6;
		gtp:intsancenum 0;
	}
	container henb_information_reporting {
		uses gtp_ies:henb_information_reporting;
		gtp_ies:order 7;
		gtp:intsancenum 0;
	}
	container indication_flags {
		uses gtp_ies:indication;
		gtp_ies:order 8;
		gtp:intsancenum 0;
	}
	container pgwfqcsid {
		uses gtp_ies:fqcsid;
		gtp_ies:order 9;
		gtp:intsancenum 0;
	}
	container sgwfqcsid {
		uses gtp_ies:fqcsid;
		gtp_ies:order 10;
		gtp:intsancenum 1;
	}
	container presence_reporting_area_action {
		uses gtp_ies:presence_reporting_area_action;
		gtp_ies:order 11;
		gtp:intsancenum 0;
	}
	container pgws_node_level_load_control_information {
		uses gtp_ies:load_control_information;
		gtp_ies:order 12;
		gtp:intsancenum 0;
	}
	container pgws_apn_level_load_control_information {
		uses gtp_ies:load_control_information;
		gtp_ies:order 13;
		gtp:intsancenum 1;
	}
	container sgws_node_level_load_control_information {
		uses gtp_ies:load_control_information;
		gtp_ies:order 14;
		gtp:intsancenum 2;
	}
	container pgws_overload_control_information {
		uses gtp_ies:overload_control_information;
		gtp_ies:order 15;
		gtp:intsancenum 0;
	}
	container sgws_overload_control_information {
		uses gtp_ies:overload_control_information;
		gtp_ies:order 16;
		gtp:intsancenum 1;
	}
	container nbifom_container {
		uses gtp_ies:fcontainer;
		gtp_ies:order 17;
		gtp:intsancenum 0;
	}
	container private_extension {
		uses gtp_ies:private_extension;
		gtp_ies:order 18;
	}
}
grouping update_bearer_request__bearer_context {
	gtp_ies:ie-type 93;
	gtp:containingMessage 97;
	container eps_bearer_id {
		uses gtp_ies:ebi;
		gtp_ies:order 1;
		gtp:iemandatory;
		gtp:intsancenum 0;
	}
	container tft {
		uses gtp_ies:bearer_tft;
		gtp_ies:order 2;
		gtp:intsancenum 0;
	}
	container bearer_level_qos {
		uses gtp_ies:bearer_qos;
		gtp_ies:order 3;
		gtp:intsancenum 0;
	}
	container bearer_flags {
		uses gtp_ies:bearer_flags;
		gtp_ies:order 4;
		gtp:intsancenum 0;
	}
	container protocol_configuration_options {
		uses gtp_ies:pco;
		gtp_ies:order 5;
		gtp:intsancenum 0;
	}
	container extended_protocol_configuration_options {
		uses gtp_ies:epco;
		gtp_ies:order 7;
		gtp:intsancenum 0;
	}
	container maximum_packet_loss_rate {
		uses gtp_ies:maximum_packet_loss_rate;
		gtp_ies:order 8;
		gtp:intsancenum 0;
	}
}
grouping update_bearer_request__load_control_information {
	gtp_ies:ie-type 181;
	gtp:containingMessage 97;
	container load_control_sequence_number {
		uses gtp_ies:sequence_number;
		gtp_ies:order 1;
		gtp:iemandatory;
		gtp:intsancenum 0;
	}
	container load_metric {
		uses gtp_ies:metric;
		gtp_ies:order 2;
		gtp:iemandatory;
		gtp:intsancenum 0;
	}
	container list_of_apn_and_relative_capacity {
		uses gtp_ies:apn_and_relative_capacity;
		gtp_ies:order 3;
		gtp:intsancenum 0;
	}
}
grouping update_bearer_request__overload_control_information {
	gtp_ies:ie-type 180;
	gtp:containingMessage 97;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping update_bearer_response {
	gtp:messageType "response";
	container cause {
		uses gtp_ies:cause;
		gtp_ies:order 1;
		gtp:iemandatory;
		gtp:intsancenum 0;
	}
	container bearer_contexts {
		uses gtp_ies:bearer_context_;
		gtp_ies:order 2;
		gtp:iemandatory;
		gtp:intsancenum 0;
	}
	container protocol_configuration_options {
		uses gtp_ies:pco;
		gtp_ies:order 3;
		gtp:intsancenum 0;
	}
	container recovery {
		uses gtp_ies:recovery;
		gtp_ies:order 4;
		gtp:intsancenum 0;
	}
	container mmefqcsid {
		uses gtp_ies:fqcsid;
		gtp_ies:order 5;
		gtp:intsancenum 0;
	}
	container sgwfqcsid {
		uses gtp_ies:fqcsid;
		gtp_ies:order 6;
		gtp:intsancenum 1;
	}
	container epdgfqcsid {
		uses gtp_ies:fqcsid;
		gtp_ies:order 7;
		gtp:intsancenum 2;
	}
	container twanfqcsid {
		uses gtp_ies:fqcsid;
		gtp_ies:order 8;
		gtp:intsancenum 3;
	}
	container indication_flags {
		uses gtp_ies:indication;
		gtp_ies:order 9;
		gtp:intsancenum 0;
	}
	container ue_time_zone {
		uses gtp_ies:ue_time_zone;
		gtp_ies:order 10;
		gtp:intsancenum 0;
	}
	container user_location_information {
		uses gtp_ies:uli;
		gtp_ies:order 11;
		gtp:intsancenum 0;
	}
	container twan_identifier {
		uses gtp_ies:twan_identifier;
		gtp_ies:order 12;
		gtp:intsancenum 0;
	}
	container mmes4sgsns_overload_control_information {
		uses gtp_ies:overload_control_information;
		gtp_ies:order 13;
		gtp:intsancenum 0;
	}
	container sgws_overload_control_information {
		uses gtp_ies:overload_control_information;
		gtp_ies:order 14;
		gtp:intsancenum 1;
	}
	container presence_reporting_area_information {
		uses gtp_ies:presence_reporting_area_information;
		gtp_ies:order 15;
		gtp:intsancenum 0;
	}
	container mmes4sgsn_identifier {
		uses gtp_ies:ip_address;
		gtp_ies:order 16;
		gtp:intsancenum 0;
	}
	container twanepdgs_overload_control_information {
		uses gtp_ies:overload_control_information;
		gtp_ies:order 17;
		gtp:intsancenum 2;
	}
	container wlan_location_information {
		uses gtp_ies:twan_identifier;
		gtp_ies:order 18;
		gtp:intsancenum 1;
	}
	container wlan_location_timestamp {
		uses gtp_ies:twan_identifier_timestamp;
		gtp_ies:order 19;
		gtp:intsancenum 1;
	}
	container ue_local_ip_address {
		uses gtp_ies:ip_address;
		gtp_ies:order 20;
		gtp:intsancenum 0;
	}
	container ue_udp_port {
		uses gtp_ies:port_number;
		gtp_ies:order 21;
		gtp:intsancenum 0;
	}
	container nbifom_container {
		uses gtp_ies:fcontainer;
		gtp_ies:order 22;
		gtp:intsancenum 0;
	}
	container ue_tcp_port {
		uses gtp_ies:port_number;
		gtp_ies:order 23;
		gtp:intsancenum 1;
	}
	container private_extension {
		uses gtp_ies:private_extension;
		gtp_ies:order 24;
	}
}
grouping update_bearer_response__bearer_context {
	gtp_ies:ie-type 93;
	gtp:containingMessage 98;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s4u_sgsn_fteid {
		uses gtp_ies:fteid;
		gtp_ies:order 3;
		gtp:intsancenum 0;
	}
	container s12_rnc_fteid {
		uses gtp_ies:fteid;
		gtp_ies:order 4;
		gtp:intsancenum 1;
	}
	container protocol_configuration_options {
		uses gtp_ies:pco;
		gtp_ies:order 5;
		gtp:intsancenum 0;
	}
	container rannas_cause {
		uses gtp_ies:rannas_cause;
		gtp_ies:order 6;
		gtp:intsancenum 0;
	}
	container extended_protocol_configuration_options {
		uses gtp_ies:epco;
		gtp_ies:order 7;
		gtp:intsancenum 0;
	}
}
grouping update_bearer_response__overload_control_information {
	gtp_ies:ie-type 180;
	gtp:containingMessage 98;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping delete_bearer_command {
	gtp:messageType "command";
	container bearer_contexts {
		uses gtp_ies:bearer_context_;
		gtp_ies:order 1;
		gtp:iemandatory;
		gtp:intsancenum 0;
	}
	container user_location_information {
		uses gtp_ies:uli;
		gtp_ies:order 2;
		gtp:intsancenum 0;
	}
	container uli_timestamp {
		uses gtp_ies:uli_timestamp;
		gtp_ies:order 3;
		gtp:intsancenum 0;
	}
	container ue_time_zone {
		uses gtp_ies:ue_time_zone;
		gtp_ies:order 4;
		gtp:intsancenum 0;
	}
	container mmes4sgsns_overload_control_information {
		uses gtp_ies:overload_control_information;
		gtp_ies:order 5;
		gtp:intsancenum 0;
	}
	container sgws_overload_control_information {
		uses gtp_ies:overload_control_information;
		gtp_ies:order 6;
		gtp:intsancenum 1;
	}
	container sender_fteid_for_control_plane {
		uses gtp_ies:fteid;
		gtp_ies:order 7;
		gtp:intsancenum 0;
	}
	container secondary_rat_usage_data_report {
		uses gtp_ies:secondary_rat_usage_data_report;
		gtp_ies:order 8;
		gtp:intsancenum 0;
	}
	container private_extension {
		uses gtp_ies:private_extension;
		gtp_ies:order 9;
	}
}
grouping delete_bearer_command__bearer_context {
	gtp_ies:ie-type 93;
	container eps_bearer_id {
		uses gtp_ies:ebi;
		gtp_ies:order 1;
		gtp:iemandatory;
		gtp:intsancenum 0;
	}
	container bearer_flags {
		uses gtp_ies:bearer_flags;
		gtp_ies:order 2;
		gtp:intsancenum 0;
		description "Applicable flags are:
VB (Voice Bearer) indicator shall be set to indicate a voice bearer for PS-to-CS (v)SRVCC handover.
Vind (vSRVCC indicator) indicator shall be set to indicate a video bearer for PS-to-CS vSRVCC handover.
";
	}
	container rannas_release_cause {
		uses gtp_ies:rannas_cause;
		gtp_ies:order 3;
		gtp:intsancenum 0;
		description "The MME shall include this IE on the S11 interface to indicate the RAN release cause and/or NAS release cause to release the bearer, if available and this information is permitted to be sent to the PGW operator according to MME operators policy. 
If both a RAN release cause and a NAS release cause are generated, then several IEs with the same type and instance value shall be included to represent a list of causes.
The SGW shall include this IE on the S5/S8 interface if it receives it from the MME.
";
	}
}
grouping delete_bearer_command__overload_control_information {
	gtp_ies:ie-type 180;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping delete_bearer_failure_indication {
	gtp:messageType "indication";
	container cause {
		uses gtp_ies:cause;
		gtp_ies:order 1;
		gtp:iemandatory;
		gtp:intsancenum 0;
	}
	container bearer_context {
		uses gtp_ies:bearer_context_;
		gtp_ies:order 2;
		gtp:iemandatory;
		gtp:intsancenum 0;
	}
	container recovery {
		uses gtp_ies:recovery;
		gtp_ies:order 3;
		gtp:intsancenum 0;
	}
	container indication_flags {
		uses gtp_ies:indication;
		gtp_ies:order 4;
		gtp:intsancenum 0;
	}
	container pgws_overload_control_information {
		uses gtp_ies:overload_control_information;
		gtp_ies:order 5;
		gtp:intsancenum 0;
	}
	container sgws_overload_control_information {
		uses gtp_ies:overload_control_information;
		gtp_ies:order 6;
		gtp:intsancenum 1;
	}
	container private_extension {
		uses gtp_ies:private_extension;
		gtp_ies:order 7;
	}
}
grouping delete_bearer_failure_indication__bearer_context {
	gtp_ies:ie-type 93;
	container eps_bearer_id {
		uses gtp_ies:ebi;
		gtp_ies:order 1;
		gtp:iemandatory;
		gtp:intsancenum 0;
		description "See subclause 6.1.1 Presence requirements of Information Elements.
";
	}
	container cause {
		uses gtp_ies:cause;
		gtp_ies:order 2;
		gtp:iemandatory;
		gtp:intsancenum 0;
		description "This IE shall indicate the reason of the unsuccessful handling of the bearer.
";
	}
}
grouping delete_bearer_failure_indication__overload_control_information {
	gtp_ies:ie-type 180;
	container overload_control_sequence_number {
		uses gtp_ies:sequence_number;
		gtp_ies:order 1;
		gtp:iemandatory;
		gtp:intsancenum 0;
	}
	container overload_reduction_metric {
		uses gtp_ies:metric;
		gtp_ies:order 2;
		gtp:iemandatory;
		gtp:intsancenum 0;
	}
	container period_of_validity {
		uses gtp_ies:epc_timer;
		gtp_ies:order 3;
		gtp:iemandatory;
		gtp:intsancenum 0;
	}
	container list_of_access_point_name {
		uses gtp_ies:apn;
		gtp_ies:order 4;
		gtp:intsancenum 0;
	}
}
grouping create_indirect_data_forwarding_tunnel_request {
	gtp:messageType "request";
	container imsi {
		uses gtp_ies:imsi;
		gtp_ies:order 1;
		gtp:intsancenum 0;
	}
	container me_identity {
		uses gtp_ies:mei;
		gtp_ies:order 2;
		gtp:intsancenum 0;
	}
	container indication_flags {
		uses gtp_ies:indication;
		gtp_ies:order 3;
		gtp:intsancenum 0;
	}
	container sender_fteid_for_control_plane {
		uses gtp_ies:fteid;
		gtp_ies:order 4;
		gtp:intsancenum 0;
	}
	container bearer_contexts {
		uses gtp_ies:bearer_context_;
		gtp_ies:order 5;
		gtp:iemandatory;
		gtp:intsancenum 0;
	}
	container recovery {
		uses gtp_ies:recovery;
		gtp_ies:order 6;
		gtp:intsancenum 0;
	}
	container private_extension {
		uses gtp_ies:private_extension;
		gtp_ies:order 7;
	}
}
grouping create_indirect_data_forwarding_tunnel_request__bearer_context {
	gtp_ies:ie-type 93;
	gtp:containingMessage 166;
	container eps_bearer_id {
		uses gtp_ies:ebi;
		gtp_ies:order 1;
		gtp:iemandatory;
		gtp:intsancenum 0;
	}
	container enodeb_fteid_for_dl_data_forwarding {
		uses gtp_ies:fteid;
		gtp_ies:order 2;
		gtp:intsancenum 0;
	}
	container sgsn_fteid_for_dl_data_forwarding {
		uses gtp_ies:fteid;
		gtp_ies:order 3;
		gtp:intsancenum 2;
	}
	container rnc_fteid_for_dl_data_forwarding {
		uses gtp_ies:fteid;
		gtp_ies:order 4;
		gtp:intsancenum 3;
	}
	container enodeb_fteid_for_ul_data_forwarding {
		uses gtp_ies:fteid;
		gtp_ies:order 5;
		gtp:intsancenum 4;
	}
	container sgw_fteid_for_ul_data_forwarding {
		uses gtp_ies:fteid;
		gtp_ies:order 6;
		gtp:intsancenum 5;
	}
	container mme_fteid_for_dl_data_forwarding {
		uses gtp_ies:fteid;
		gtp_ies:order 7;
		gtp:intsancenum 6;
	}
}
grouping create_indirect_data_forwarding_tunnel_response {
	gtp:messageType "response";
	container cause {
		uses gtp_ies:cause;
		gtp_ies:order 1;
		gtp:iemandatory;
		gtp:intsancenum 0;
	}
	container sender_fteid_for_control_plane {
		uses gtp_ies:fteid;
		gtp_ies:order 2;
		gtp:intsancenum 0;
		description "This IE shall be included by an SGW if the SGW receives a Sender F-TEID for Control Plane IE from an MME/SGSN in a Create Indirect Data Forwarding Tunnel Request message.
See also NOTE 1 in Table 7.2.18-1.
";
	}
	container bearer_contexts {
		uses gtp_ies:bearer_context_;
		gtp_ies:order 3;
		gtp:iemandatory;
		gtp:intsancenum 0;
		description "Several IEs with this type and instance value may be included as necessary to represent a list of Bearers
";
	}
	container recovery {
		uses gtp_ies:recovery;
		gtp_ies:order 4;
		gtp:intsancenum 0;
		description "This IE shall be included if contacting the peer for the first time
";
	}
	container private_extension {
		uses gtp_ies:private_extension;
		gtp_ies:order 5;
	}
}
grouping create_indirect_data_forwarding_tunnel_response__bearer_context {
	gtp_ies:ie-type 93;
	gtp:containingMessage 167;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s1u_sgw_fteid_for_dl_data_forwarding {
		uses gtp_ies:fteid;
		gtp_ies:order 3;
		gtp:intsancenum 0;
	}
	container s12_sgw_fteid_for_dl_data_forwarding {
		uses gtp_ies:fteid;
		gtp_ies:order 4;
		gtp:intsancenum 1;
	}
	container s4u_sgw_fteid_for_dl_data_forwarding {
		uses gtp_ies:fteid;
		gtp_ies:order 5;
		gtp:intsancenum 2;
	}
	container sgw_fteid_for_dl_data_forwarding {
		uses gtp_ies:fteid;
		gtp_ies:order 6;
		gtp:intsancenum 3;
	}
	container s1u_sgw_fteid_for_ul_data_forwarding {
		uses gtp_ies:fteid;
		gtp_ies:order 7;
		gtp:intsancenum 4;
	}
	container sgw_fteid_for_ul_data_forwarding {
		uses gtp_ies:fteid;
		gtp_ies:order 8;
		gtp:intsancenum 5;
	}
}
grouping release_access_bearers_response__load_control_information {
	gtp_ies:ie-type 181;
	gtp:containingMessage 171;
	container load_control_sequence_number {
		uses gtp_ies:sequence_number;
		gtp_ies:order 1;
		gtp:iemandatory;
		gtp:intsancenum 0;
		description "See clause 12.2.5.1.2.1 for the description and use of this parameter.
";
	}
	container load_metric {
		uses gtp_ies:metric;
		gtp_ies:order 2;
		gtp:iemandatory;
		gtp:intsancenum 0;
		description "See clause 12.2.5.1.2.2 for the description and use of this parameter.
";
	}
}
grouping release_access_bearers_response__overload_control_information {
	gtp_ies:ie-type 180;
	gtp:containingMessage 171;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping stop_paging_indication {
	gtp:messageType "indication";
	container imsi {
		uses gtp_ies:imsi;
		gtp_ies:order 1;
		gtp:intsancenum 0;
		description "This IE shall be included on the S11/S4 interface when the Stop Paging Indication message is sent to the restarted CN node (or another node in the same pool) as part of the network triggered service restoration procedure with ISR (see 3GPP TS 23.007 [17]).
";
	}
	container private_extension {
		uses gtp_ies:private_extension;
		gtp_ies:order 2;
	}
}
grouping modify_access_bearers_request {
	gtp:messageType "request";
	container indication_flags {
		uses gtp_ies:indication;
		gtp_ies:order 1;
		gtp:intsancenum 0;
	}
	container sender_fteid_for_control_plane {
		uses gtp_ies:fteid;
		gtp_ies:order 2;
		gtp:intsancenum 0;
	}
	container delay_downlink_packet_notification_request {
		uses gtp_ies:delay_value;
		gtp_ies:order 3;
		gtp:intsancenum 0;
	}
	container bearer_contexts_to_be_modified {
		uses gtp_ies:bearer_context;
		gtp_ies:order 4;
		gtp:intsancenum 0;
	}
	container bearer_contexts_to_be_removed {
		uses gtp_ies:bearer_context;
		gtp_ies:order 5;
		gtp:intsancenum 1;
	}
	container recovery {
		uses gtp_ies:recovery;
		gtp_ies:order 6;
		gtp:intsancenum 0;
	}
	container secondary_rat_usage_data_report {
		uses gtp_ies:secondary_rat_usage_data_report;
		gtp_ies:order 7;
		gtp:intsancenum 0;
	}
	container private_extension {
		uses gtp_ies:private_extension;
		gtp_ies:order 8;
	}
}
grouping modify_access_bearers_request__bearer_context_to_be_modified {
	gtp_ies:ie-type 93;
	gtp:containingMessage 211;
	container eps_bearer_id {
		uses gtp_ies:ebi;
		gtp_ies:order 1;
		gtp:iemandatory;
		gtp:intsancenum 0;
	}
	container s1u_enodeb_fteid {
		uses gtp_ies:fteid;
		gtp_ies:order 2;
		gtp:intsancenum 0;
	}
	container s11u_mme_fteid {
		uses gtp_ies:fteid;
		gtp_ies:order 3;
		gtp:intsancenum 1;
	}
}
grouping modify_access_bearers_request__bearer_context_to_be_removed {
	gtp_ies:ie-type 93;
	gtp:containingMessage 211;
	container eps_bearer_id {
		uses gtp_ies:ebi;
		gtp_ies:order 1;
		gtp:iemandatory;
		gtp:intsancenum 0;
	}
}
grouping modify_access_bearers_response {
	gtp:messageType "response";
	container cause {
		uses gtp_ies:cause;
		gtp_ies:order 1;
		gtp:iemandatory;
		gtp:intsancenum 0;
	}
	container bearer_contexts_modified {
		uses gtp_ies:bearer_context;
		gtp_ies:order 2;
		gtp:intsancenum 0;
	}
	container bearer_contexts_marked_for_removal {
		uses gtp_ies:bearer_context;
		gtp_ies:order 3;
		gtp:intsancenum 1;
	}
	container recovery {
		uses gtp_ies:recovery;
		gtp_ies:order 4;
		gtp:intsancenum 0;
	}
	container indication_flags {
		uses gtp_ies:indication;
		gtp_ies:order 5;
		gtp:intsancenum 0;
	}
	container sgws_node_level_load_control_information {
		uses gtp_ies:load_control_information;
		gtp_ies:order 6;
		gtp:intsancenum 0;
	}
	container sgws_overload_control_information {
		uses gtp_ies:overload_control_information;
		gtp_ies:order 7;
		gtp:intsancenum 0;
	}
	container private_extension {
		uses gtp_ies:private_extension;
		gtp_ies:order 8;
	}
}
grouping modify_access_bearers_response__bearer_context_modified {
	gtp_ies:ie-type 93;
	gtp:containingMessage 212;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
	}
	container s1u_sgw_fteid {
		uses gtp_ies:fteid;
		gtp_ies:order 3;
		gtp:intsancenum 0;
	}
	container s11u_sgw_fteid {
		uses gtp_ies:fteid;
		gtp_ies:order 4;
		gtp:intsancenum 1;
	}
}
grouping modify_access_bearers_response__bearer_context_marked_for_removal {
	gtp_ies:ie-type 93;
	gtp:containingMessage 212;
	container eps_bearer_id {
		uses gtp_ies:ebi;
		gtp_ies:order 1;
		gtp:iemandatory;
		gtp:intsancenum 0;
	}
	container cause {
		uses gtp_ies:cause;
		gtp_ies:order 2;
		gtp:iemandatory;
		gtp:intsancenum 0;
		description "This IE shall indicate if the bearer handling was successful, and if not, gives information on the reason.
";
	}
}
grouping modify_access_bearers_response__load_control_information {
	gtp_ies:ie-type 181;
	gtp:containingMessage 212;
	container load_control_sequence_number {
		uses gtp_ies:sequence_number;
		gtp_ies:order 1;
		gtp:iemandatory;
		gtp:intsancenum 0;
		description "See clause 12.2.5.1.2.1 for the description and use of this parameter.
";
	}
	container load_metric {
		uses gtp_ies:metric;
		gtp_ies:order 2;
		gtp:iemandatory;
		gtp:intsancenum 0;
		description "See clause 12.2.5.1.2.2 for the description and use of this parameter.
";
	}
}
grouping modify_access_bearers_response__overload_control_information {
	gtp_ies:ie-type 180;
	gtp:containingMessage 212;
	container overload_control_sequence_number {
		uses gtp_ies:sequence_number;
		gtp_ies:order 1;
		gtp:iemandatory;
		gtp:intsancenum 0;
		description "See clause 12.3.5.1.2.1 for the description and use of this parameter.
";
	}
	container overload_reduction_metric {
		uses gtp_ies:metric;
		gtp_ies:order 2;
		gtp:iemandatory;
		gtp:intsancenum 0;
		description "See clause 12.3.5.1.2.3 for the description and use of this parameter.
";
	}
	container period_of_validity {
		uses gtp_ies:epc_timer;
		gtp_ies:order 3;
		gtp:iemandatory;
		gtp:intsancenum 0;
		description "See clause 12.3.5.1.2.2 for the description and use of this parameter.
This IE should be set to 0 if the Overload Reduction Metric is null. This IE shall be ignored by the receiver if the Overload Reduction Metric is null.
";
	}
}
grouping remote_ue_report_notification {
	gtp:messageType "notification";
	gtp:messageTypeValue 40;
	container remote_ue_context__connected {
		uses gtp_ies:remote_ue_context;
		gtp_ies:order 1;
		gtp:intsancenum 0;
		description "This IE shall be sent on the S11 interface and S5/S8 interface when the MME receives a report from the ProSe UE-to-Network Relay that a remote UE is newly connected.

The SGW shall forward this IE to the PGW.

Several IEs with the same type and instance value may be included as necessary to represent a list of remote UEs newly connected.
";
	}
	container remote_ue_context_disconnected {
		uses gtp_ies:remote_ue_context;
		gtp_ies:order 2;
		gtp:intsancenum 1;
		description "This IE shall be sent on the S11 interface and S5/S8 interface when the MME receives a report from the ProSe UE-to-Network Relay that a remote UE is newly disconnected.

The SGW shall forward this IE to the PGW.

Several IEs with the same type and instance value may be included as necessary to represent a list of remote UEs newly disconnected.
";
	}
	container private_extension {
		uses gtp_ies:private_extension;
		gtp_ies:order 3;
	}
}
grouping remote_ue_report_notification__remote_ue_context_connected {
	gtp_ies:ie-type 191;
	gtp:containingMessage 40;
	container remote_user_id {
		uses gtp_ies:remote_user_id;
		gtp_ies:order 1;
		gtp:iemandatory;
		gtp:intsancenum 0;
		description "See subclause 8.123 for the description and use of this parameter
";
	}
	container remote_ue_ip_information {
		uses gtp_ies:remote_ue_ip_information;
		gtp_ies:order 2;
		gtp:iemandatory;
		gtp:intsancenum 0;
		description "See subclause 8.124 for the description and use of this parameter
";
	}
}
grouping remote_ue_report_notification___remote_ue_context_disconnected {
	gtp_ies:ie-type 191;
	container remote_user_id {
		uses gtp_ies:remote_user_id;
		gtp_ies:order 1;
		gtp:iemandatory;
		gtp:intsancenum 0;
		description "See subclause 8.123 for the description and use of this parameter
";
	}
}
grouping remote_ue_report_acknowledge {
	gtp:messageType "acknowledge";
	gtp:messageTypeValue 41;
	container cause {
		uses gtp_ies:cause;
		gtp_ies:order 1;
		gtp:iemandatory;
		gtp:intsancenum 0;
	}
	container private_extension {
		uses gtp_ies:private_extension;
		gtp_ies:order 2;
	}
}
grouping forward_relocation_request {
	gtp:messageType "request";
	container imsi {
		uses gtp_ies:imsi;
		gtp_ies:order 1;
		gtp:intsancenum 0;
	}
	container senders_fteid_for_control_plane {
		uses gtp_ies:fteid;
		gtp_ies:order 2;
		gtp:iemandatory;
		gtp:intsancenum 0;
	}
	container mmesgsnamf_ue_eps_pdn_connections {
		uses gtp_ies:pdn_connection_;
		gtp_ies:order 3;
		gtp:intsancenum 0;
	}
	container sgw_s11s4_ip_address_and_teid_for_control_plane {
		uses gtp_ies:fteid;
		gtp_ies:order 4;
		gtp:intsancenum 1;
	}
	container sgw_node_name {
		uses gtp_ies:fqdn;
		gtp_ies:order 5;
		gtp:intsancenum 0;
	}
	container mmesgsnamf_ue_mm_context {
		uses gtp_ies:mm_context;
		gtp_ies:order 6;
		gtp:iemandatory;
		gtp:intsancenum 0;
	}
	container indication_flags {
		uses gtp_ies:indication;
		gtp_ies:order 7;
		gtp:intsancenum 0;
	}
	container eutran_transparent_container {
		uses gtp_ies:fcontainer;
		gtp_ies:order 8;
		gtp:intsancenum 0;
	}
	container utran_transparent_container {
		uses gtp_ies:fcontainer;
		gtp_ies:order 9;
		gtp:intsancenum 1;
	}
	container bss_container {
		uses gtp_ies:fcontainer;
		gtp_ies:order 10;
		gtp:intsancenum 2;
	}
	container target_identification {
		uses gtp_ies:target_identification;
		gtp_ies:order 11;
		gtp:intsancenum 0;
	}
	container hrpd_access_node_s101_ip_address {
		uses gtp_ies:ipaddress;
		gtp_ies:order 12;
		gtp:intsancenum 0;
	}
	container onexiws_s102_ip_address {
		uses gtp_ies:ipaddress;
		gtp_ies:order 13;
		gtp:intsancenum 1;
	}
	container s1ap_cause {
		uses gtp_ies:fcause;
		gtp_ies:order 14;
		gtp:intsancenum 0;
	}
	container ranap_cause {
		uses gtp_ies:fcause;
		gtp_ies:order 15;
		gtp:intsancenum 1;
	}
	container bssgp_cause {
		uses gtp_ies:fcause;
		gtp_ies:order 16;
		gtp:intsancenum 2;
	}
	container source_identification {
		uses gtp_ies:source_identification;
		gtp_ies:order 17;
		gtp:intsancenum 0;
	}
	container selected_plmn_id {
		uses gtp_ies:plmn_id;
		gtp_ies:order 18;
		gtp:intsancenum 0;
	}
	container recovery {
		uses gtp_ies:recovery;
		gtp_ies:order 19;
		gtp:intsancenum 0;
	}
	container trace_information {
		uses gtp_ies:trace_information;
		gtp_ies:order 20;
		gtp:intsancenum 0;
	}
	container subscribed_rfsp_index {
		uses gtp_ies:rfsp_index;
		gtp_ies:order 21;
		gtp:intsancenum 0;
	}
	container rfsp_index_in_use {
		uses gtp_ies:rfsp_index;
		gtp_ies:order 22;
		gtp:intsancenum 1;
	}
	container csg_id {
		uses gtp_ies:csg_id;
		gtp_ies:order 23;
		gtp:intsancenum 0;
	}
	container csg_membership_indication {
		uses gtp_ies:cmi;
		gtp_ies:order 24;
		gtp:intsancenum 0;
	}
	container ue_time_zone {
		uses gtp_ies:ue_time_zone;
		gtp_ies:order 25;
		gtp:intsancenum 0;
	}
	container serving_network {
		uses gtp_ies:serving_network;
		gtp_ies:order 26;
		gtp:intsancenum 0;
	}
	container additional_mm_context_for_srvcc {
		uses gtp_ies:additional_mm_context_for_srvcc;
		gtp_ies:order 28;
		gtp:intsancenum 0;
	}
	container additional_flags_for_srvcc {
		uses gtp_ies:additional_flags_for_srvcc;
		gtp_ies:order 29;
		gtp:intsancenum 0;
	}
	container stnsr {
		uses gtp_ies:stnsr;
		gtp_ies:order 30;
		gtp:intsancenum 0;
	}
	container cmsisdn {
		uses gtp_ies:msisdn;
		gtp_ies:order 31;
		gtp:intsancenum 0;
	}
	container mdt_configuration {
		uses gtp_ies:mdt_configuration;
		gtp_ies:order 32;
		gtp:intsancenum 0;
	}
	container sgsn_node_name {
		uses gtp_ies:fqdn;
		gtp_ies:order 33;
		gtp:intsancenum 1;
	}
	container mme_node_name {
		uses gtp_ies:fqdn;
		gtp_ies:order 34;
		gtp:intsancenum 2;
	}
	container user_csg_information {
		uses gtp_ies:uci;
		gtp_ies:order 35;
		gtp:intsancenum 0;
	}
	container monitoring_event_information {
		uses gtp_ies:monitoring_event_information;
		gtp_ies:order 36;
		gtp:intsancenum 0;
	}
	container ue_usage_type {
		uses gtp_ies:integer_number;
		gtp_ies:order 37;
		gtp:intsancenum 0;
	}
	container mmesgsn_ue_scef_pdn_connections {
		uses gtp_ies:scef_pdn_connection;
		gtp_ies:order 38;
		gtp:intsancenum 0;
	}
	container msisdn {
		uses gtp_ies:msisdn;
		gtp_ies:order 39;
		gtp:intsancenum 1;
	}
	container source_udp_port_number {
		uses gtp_ies:port_number;
		gtp_ies:order 40;
		gtp:intsancenum 0;
	}
	container serving_plmn_rate_control {
		uses gtp_ies:serving_plmn_rate_control;
		gtp_ies:order 41;
		gtp:intsancenum 0;
	}
	container private_extension {
		uses gtp_ies:private_extension;
		gtp_ies:order 42;
	}
}
grouping forward_relocation_request__mmesgsnamf_ue_eps_pdn_connections {
	gtp_ies:ie-type 109;
	gtp:containingMessage 133;
	container apn {
		uses gtp_ies:apn;
		gtp_ies:order 1;
		gtp:iemandatory;
		gtp:intsancenum 0;
	}
	container apn_restriction {
		uses gtp_ies:apn_restriction;
		gtp_ies:order 2;
		gtp:intsancenum 0;
	}
	container selection_mode {
		uses gtp_ies:selection_mode;
		gtp_ies:order 3;
		gtp:intsancenum 0;
	}
	container ipv4_address {
		uses gtp_ies:ip_address;
		gtp_ies:order 4;
		gtp:intsancenum 0;
	}
	container ipv6_address {
		uses gtp_ies:ip_address;
		gtp_ies:order 5;
		gtp:intsancenum 1;
	}
	container linked_eps_bearer_id {
		uses gtp_ies:ebi;
		gtp_ies:order 6;
		gtp:iemandatory;
		gtp:intsancenum 0;
	}
	container pgw_s5s8_ip_address_for_control_plane_or_pmip {
		uses gtp_ies:fteid;
		gtp_ies:order 7;
		gtp:iemandatory;
		gtp:intsancenum 0;
	}
	container bearer_contexts {
		uses gtp_ies:bearer_context;
		gtp_ies:order 8;
		gtp:intsancenum 0;
	}
	container aggregate_maximum_bit_rate {
		uses gtp_ies:ambr;
		gtp_ies:order 9;
		gtp:iemandatory;
		gtp:intsancenum 0;
	}
	container charging_characteristics {
		uses gtp_ies:charging_characteristics;
		gtp_ies:order 10;
		gtp:intsancenum 0;
	}
	container change_reporting_action {
		uses gtp_ies:change_reporting_action;
		gtp_ies:order 11;
		gtp:intsancenum 0;
	}
	container csg_information_reporting_action {
		uses gtp_ies:csg_information_reporting_action;
		gtp_ies:order 12;
		gtp:intsancenum 0;
	}
	container henb_information_reporting {
		uses gtp_ies:henb_information_reporting;
		gtp_ies:order 13;
		gtp:intsancenum 0;
	}
	container indication_flags {
		uses gtp_ies:indication;
		gtp_ies:order 14;
		gtp:intsancenum 0;
	}
	container signalling_priority_indication {
		uses gtp_ies:signalling_priority_indication;
		gtp_ies:order 15;
		gtp:intsancenum 0;
	}
	container change_to_report_flags {
		uses gtp_ies:change_to_report_flags;
		gtp_ies:order 16;
		gtp:intsancenum 0;
	}
	container local_home_network_id {
		uses gtp_ies:fqdn;
		gtp_ies:order 17;
		gtp:intsancenum 1;
	}
	container presence_reporting_area_action {
		uses gtp_ies:presence_reporting_area_action;
		gtp_ies:order 18;
		gtp:intsancenum 0;
	}
	container wlan_offloadability_indication {
		uses gtp_ies:wlan_offloadability_messageType_indication;
		gtp_ies:order 19;
		gtp:intsancenum 0;
	}
	container remote_ue_context_connected {
		uses gtp_ies:remote_ue_context;
		gtp_ies:order 20;
		gtp:intsancenum 0;
	}
	container pdn_type {
		uses gtp_ies:pdn_type;
		gtp_ies:order 21;
		gtp:intsancenum 0;
	}
	container header_compression_configuration {
		uses gtp_ies:header_compression_configuration;
		gtp_ies:order 22;
		gtp:intsancenum 0;
	}
}
grouping forward_relocation_request__bearer_context {
	gtp_ies:ie-type 93;
	gtp:containingMessage 133;
	container eps_bearer_id {
		uses gtp_ies:ebi;
		gtp_ies:order 1;
		gtp:iemandatory;
		gtp:intsancenum 0;
	}
	container tft {
		uses gtp_ies:bearer_tft;
		gtp_ies:order 2;
		gtp:intsancenum 0;
	}
	container sgw_s1s4s12_ip_address_and_teid_for_user_plane {
		uses gtp_ies:fteid;
		gtp_ies:order 3;
		gtp:iemandatory;
		gtp:intsancenum 0;
	}
	container pgw_s5s8_ip_address_and_teid_for_user_plane {
		uses gtp_ies:fteid;
		gtp_ies:order 4;
		gtp:intsancenum 1;
	}
	container bearer_level_qos {
		uses gtp_ies:bearer_qos;
		gtp_ies:order 5;
		gtp:iemandatory;
		gtp:intsancenum 0;
	}
	container bss_container {
		uses gtp_ies:fcontainer;
		gtp_ies:order 6;
		gtp:intsancenum 0;
	}
	container transaction_identifier {
		uses gtp_ies:ti;
		gtp_ies:order 7;
		gtp:intsancenum 0;
	}
	container bearer_flags {
		uses gtp_ies:bearer_flags;
		gtp_ies:order 8;
		gtp:intsancenum 0;
	}
	container sgw_s11_ip_address_and_teid_for_user_plane {
		uses gtp_ies:fteid;
		gtp_ies:order 9;
		gtp:intsancenum 2;
	}
}
grouping forward_relocation_request__remote_ue_context_connected {
	gtp_ies:ie-type 191;
	gtp:containingMessage 133;
	container remote_user_id {
		uses gtp_ies:remote_user_id;
		gtp_ies:order 1;
		gtp:iemandatory;
		gtp:intsancenum 0;
		description "See subclause 8.123 for the description and use of this parameter
";
	}
	container remote_ue_ip_information {
		uses gtp_ies:remote_ue_ip_information;
		gtp_ies:order 2;
		gtp:iemandatory;
		gtp:intsancenum 0;
		description "See subclause 8.124 for the description and use of this parameter
";
	}
}
grouping forward_relocation_request__mme_ue_scef_pdn_connections {
	gtp_ies:ie-type 195;
	gtp:containingMessage 133;
	container apn {
		uses gtp_ies:apn;
		gtp_ies:order 1;
		gtp:iemandatory;
		gtp:intsancenum 0;
	}
	container default_eps_bearer_id {
		uses gtp_ies:ebi;
		gtp_ies:order 2;
		gtp:iemandatory;
		gtp:intsancenum 0;
		description "This IE shall identify the default bearer of the SCEF PDN Connection.
";
	}
	container scef_id {
		uses gtp_ies:node_identifier;
		gtp_ies:order 3;
		gtp:iemandatory;
		gtp:intsancenum 0;
		description "This IE shall include the SCEF Identifier and the SCEF Realm for the APN.
";
	}
}
grouping forward_relocation_response {
	gtp:messageType "response";
	container cause {
		uses gtp_ies:cause;
		gtp_ies:order 1;
		gtp:iemandatory;
		gtp:intsancenum 0;
	}
	container senders_fteid_for_control_plane {
		uses gtp_ies:fteid;
		gtp_ies:order 2;
		gtp:intsancenum 0;
	}
	container indication_flags {
		uses gtp_ies:indication;
		gtp_ies:order 3;
		gtp:intsancenum 0;
	}
	container list_of_setup_bearers {
		uses gtp_ies:bearer_context_;
		gtp_ies:order 4;
		gtp:intsancenum 0;
	}
	container list_of_setup_rabs {
		uses gtp_ies:bearer_context_;
		gtp_ies:order 5;
		gtp:intsancenum 1;
	}
	container list_of_setup_pfcs {
		uses gtp_ies:bearer_context;
		gtp_ies:order 6;
		gtp:intsancenum 2;
	}
	container s1ap_cause {
		uses gtp_ies:fcause;
		gtp_ies:order 7;
		gtp:intsancenum 0;
	}
	container ranap_cause {
		uses gtp_ies:fcause;
		gtp_ies:order 8;
		gtp:intsancenum 1;
	}
	container bssgp_cause {
		uses gtp_ies:fcause;
		gtp_ies:order 9;
		gtp:intsancenum 2;
	}
	container eutran_transparent_container {
		uses gtp_ies:fcontainer;
		gtp_ies:order 10;
		gtp:intsancenum 0;
	}
	container utran_transparent_container {
		uses gtp_ies:fcontainer;
		gtp_ies:order 11;
		gtp:intsancenum 1;
	}
	container bss_container {
		uses gtp_ies:fcontainer;
		gtp_ies:order 12;
		gtp:intsancenum 2;
	}
	container sgsn_node_name {
		uses gtp_ies:fqdn;
		gtp_ies:order 14;
		gtp:intsancenum 0;
	}
	container mme_node_name {
		uses gtp_ies:fqdn;
		gtp_ies:order 15;
		gtp:intsancenum 1;
	}
	container sgsn_number {
		uses gtp_ies:node_number;
		gtp_ies:order 16;
		gtp:intsancenum 0;
	}
	container sgsn_identifier {
		uses gtp_ies:node_identifier;
		gtp_ies:order 17;
		gtp:intsancenum 0;
	}
	container mme_identifier {
		uses gtp_ies:node_identifier;
		gtp_ies:order 18;
		gtp:intsancenum 1;
	}
	container mme_number_for_mt_sms {
		uses gtp_ies:node_number;
		gtp_ies:order 19;
		gtp:intsancenum 1;
	}
	container sgsn_identifier_for_mtsms {
		uses gtp_ies:node_identifier;
		gtp_ies:order 20;
		gtp:intsancenum 2;
	}
	container mme_identifier_for_mt_sms {
		uses gtp_ies:node_identifier;
		gtp_ies:order 21;
		gtp:intsancenum 3;
	}
	container list_of_setup_bearers_for_scef_pdn_connections {
		uses gtp_ies:bearer_context_;
		gtp_ies:order 22;
		gtp:intsancenum 3;
	}
	container private_extension {
		uses gtp_ies:private_extension;
		gtp_ies:order 23;
	}
}
grouping forward_relocation_complete_notification {
	gtp:messageType "notification";
	container indication_flags {
		uses gtp_ies:indication;
		gtp_ies:order 1;
		gtp:intsancenum 0;
		description "This IE shall be included if any of the flags are set to 1.
Idle mode Signalling Reduction Activation Indication: This flag shall be set to 1 if the message is used for inter-RAT handover and the UE has ISR capability. This flag is set to indicate to the source MME/SGSN whether it shall maintain the UEs context and whether it shall activate ISR.
";
	}
	container private_extension {
		uses gtp_ies:private_extension;
		gtp_ies:order 2;
	}
}
grouping forward_relocation_complete_acknowledge {
	gtp:messageType "acknowledge";
	container cause {
		uses gtp_ies:cause;
		gtp_ies:order 1;
		gtp:iemandatory;
		gtp:intsancenum 0;
	}
	container recovery {
		uses gtp_ies:recovery;
		gtp_ies:order 2;
		gtp:intsancenum 0;
	}
	container secondary_rat_usage_data_report {
		uses gtp_ies:secondary_rat_usage_data_report;
		gtp_ies:order 3;
		gtp:intsancenum 0;
	}
	container private_extension {
		uses gtp_ies:private_extension;
		gtp_ies:order 4;
	}
}
grouping context_request {
	gtp:messageType "request";
	container imsi {
		uses gtp_ies:imsi;
		gtp_ies:order 1;
		gtp:intsancenum 0;
	}
	container guti {
		uses gtp_ies:guti;
		gtp_ies:order 2;
		gtp:intsancenum 0;
	}
	container packet_tmsi {
		uses gtp_ies:ptmsi;
		gtp_ies:order 4;
		gtp:intsancenum 0;
	}
	container ptmsi_signature {
		uses gtp_ies:ptmsi_signature;
		gtp_ies:order 5;
		gtp:intsancenum 0;
	}
	container complete_tau_request_message {
		uses gtp_ies:complete_request_message;
		gtp_ies:order 6;
		gtp:intsancenum 0;
	}
	container s3s16s10n26_address_and_teid_for_control_plane {
		uses gtp_ies:fteid;
		gtp_ies:order 7;
		gtp:intsancenum 0;
	}
	container udp_source_port_number {
		uses gtp_ies:port_number;
		gtp_ies:order 8;
		gtp:intsancenum 0;
	}
	container rat_type {
		uses gtp_ies:rat_type;
		gtp_ies:order 9;
		gtp:intsancenum 0;
	}
	container indication {
		uses gtp_ies:indication;
		gtp_ies:order 10;
		gtp:intsancenum 0;
	}
	container hop_counter {
		uses gtp_ies:hop_counter;
		gtp_ies:order 11;
		gtp:intsancenum 0;
	}
	container target_plmn_id {
		uses gtp_ies:serving_network;
		gtp_ies:order 12;
		gtp:intsancenum 0;
	}
	container sgsn_node_name {
		uses gtp_ies:fqdn;
		gtp_ies:order 14;
		gtp:intsancenum 0;
	}
	container mme_node_name {
		uses gtp_ies:fqdn;
		gtp_ies:order 15;
		gtp:intsancenum 1;
	}
	container sgsn_number {
		uses gtp_ies:node_number;
		gtp_ies:order 16;
		gtp:intsancenum 0;
	}
	container sgsn_identifier {
		uses gtp_ies:node_identifier;
		gtp_ies:order 17;
		gtp:intsancenum 0;
	}
	container mme_identifier {
		uses gtp_ies:node_identifier;
		gtp_ies:order 18;
		gtp:intsancenum 1;
	}
	container ciot_optimizations_support_indication {
		uses gtp_ies:ciot_optimizations_support_indication_;
		gtp_ies:order 19;
		gtp:intsancenum 0;
	}
	container private_extension {
		uses gtp_ies:private_extension;
		gtp_ies:order 20;
	}
}
grouping context_response {
	gtp:messageType "response";
	container cause {
		uses gtp_ies:cause;
		gtp_ies:order 1;
		gtp:iemandatory;
		gtp:intsancenum 0;
	}
	container imsi {
		uses gtp_ies:imsi;
		gtp_ies:order 2;
		gtp:intsancenum 0;
	}
	container mmesgsnamf_ue_mm_context {
		uses gtp_ies:mm_context;
		gtp_ies:order 3;
		gtp:intsancenum 0;
	}
	container mmesgsnamf_ue_eps_pdn_connections {
		uses gtp_ies:pdn_connection_;
		gtp_ies:order 4;
		gtp:intsancenum 0;
	}
	container sender_fteid_for_control_plane {
		uses gtp_ies:fteid;
		gtp_ies:order 5;
		gtp:intsancenum 0;
	}
	container sgw_s11s4_ip_address_and_teid_for_control_plane {
		uses gtp_ies:fteid;
		gtp_ies:order 6;
		gtp:intsancenum 1;
	}
	container sgw_node_name {
		uses gtp_ies:fqdn;
		gtp_ies:order 7;
		gtp:intsancenum 0;
	}
	container indication_flags {
		uses gtp_ies:indication;
		gtp_ies:order 8;
		gtp:intsancenum 0;
	}
	container trace_information {
		uses gtp_ies:trace_information;
		gtp_ies:order 9;
		gtp:intsancenum 0;
	}
	container hrpd_access_node_s101_ip_address {
		uses gtp_ies:ipaddress;
		gtp_ies:order 10;
		gtp:intsancenum 0;
	}
	container onexiws_s102_ip_address {
		uses gtp_ies:ipaddress;
		gtp_ies:order 11;
		gtp:intsancenum 1;
	}
	container subscribed_rfsp_index {
		uses gtp_ies:rfsp_index;
		gtp_ies:order 12;
		gtp:intsancenum 0;
	}
	container rfsp_index_in_use {
		uses gtp_ies:rfsp_index;
		gtp_ies:order 13;
		gtp:intsancenum 1;
	}
	container ue_time_zone {
		uses gtp_ies:ue_time_zone;
		gtp_ies:order 14;
		gtp:intsancenum 0;
	}
	container mdt_configuration {
		uses gtp_ies:mdt_configuration;
		gtp_ies:order 16;
		gtp:intsancenum 0;
	}
	container sgsn_node_name {
		uses gtp_ies:fqdn;
		gtp_ies:order 17;
		gtp:intsancenum 1;
	}
	container mme_node_name {
		uses gtp_ies:fqdn;
		gtp_ies:order 18;
		gtp:intsancenum 2;
	}
	container user_csg_information {
		uses gtp_ies:uci;
		gtp_ies:order 19;
		gtp:intsancenum 0;
	}
	container monitoring_event_information {
		uses gtp_ies:monitoring_event_information;
		gtp_ies:order 20;
		gtp:intsancenum 0;
	}
	container ue_usage_type {
		uses gtp_ies:integer_number;
		gtp_ies:order 21;
		gtp:intsancenum 0;
	}
	container mmesgsn_ue_scef_pdn_connections {
		uses gtp_ies:scef_pdn_connection_;
		gtp_ies:order 22;
		gtp:intsancenum 0;
	}
	container rat_type {
		uses gtp_ies:rat_type;
		gtp_ies:order 23;
		gtp:intsancenum 0;
	}
	container serving_plmn_rate_control {
		uses gtp_ies:serving_plmn_rate_control;
		gtp_ies:order 24;
		gtp:intsancenum 0;
	}
	container mo_exception_data_counter {
		uses gtp_ies:counter;
		gtp_ies:order 25;
		gtp:intsancenum 0;
	}
	container remaining_running_service_gap_timer {
		uses gtp_ies:integer_number;
		gtp_ies:order 26;
		gtp:intsancenum 1;
	}
	container private_extension {
		uses gtp_ies:private_extension;
		gtp_ies:order 27;
	}
}
grouping context_response__mmesgsn_ue_eps_pdn_connections {
	gtp_ies:ie-type 109;
	gtp:containingMessage 131;
	container apn {
		uses gtp_ies:apn;
		gtp_ies:order 1;
		gtp:iemandatory;
		gtp:intsancenum 0;
	}
	container apn_restriction {
		uses gtp_ies:apn_restriction;
		gtp_ies:order 2;
		gtp:intsancenum 0;
	}
	container selection_mode {
		uses gtp_ies:selection_mode;
		gtp_ies:order 3;
		gtp:intsancenum 0;
	}
	container ipv4_address {
		uses gtp_ies:ip_address;
		gtp_ies:order 4;
		gtp:intsancenum 0;
	}
	container ipv6_address {
		uses gtp_ies:ip_address;
		gtp_ies:order 5;
		gtp:intsancenum 1;
	}
	container linked_eps_bearer_id {
		uses gtp_ies:ebi;
		gtp_ies:order 6;
		gtp:iemandatory;
		gtp:intsancenum 0;
	}
	container pgw_s5s8_ip_address_for_control_plane_or_pmip {
		uses gtp_ies:fteid;
		gtp_ies:order 7;
		gtp:iemandatory;
		gtp:intsancenum 0;
	}
	container pgw_node_name {
		uses gtp_ies:fqdn;
		gtp_ies:order 8;
		gtp:intsancenum 0;
	}
	container bearer_contexts {
		uses gtp_ies:bearer_context;
		gtp_ies:order 9;
		gtp:iemandatory;
		gtp:intsancenum 0;
	}
	container aggregate_maximum_bit_rate {
		uses gtp_ies:ambr;
		gtp_ies:order 10;
		gtp:iemandatory;
		gtp:intsancenum 0;
	}
	container charging_characteristics {
		uses gtp_ies:charging_characteristics;
		gtp_ies:order 11;
		gtp:intsancenum 0;
	}
	container change_reporting_action {
		uses gtp_ies:change_reporting_action;
		gtp_ies:order 12;
		gtp:intsancenum 0;
	}
	container csg_information_reporting_action {
		uses gtp_ies:csg_information_reporting_action;
		gtp_ies:order 13;
		gtp:intsancenum 0;
	}
	container henb_information_reporting {
		uses gtp_ies:henb_information_reporting;
		gtp_ies:order 14;
		gtp:intsancenum 0;
	}
	container indication_flags {
		uses gtp_ies:indication;
		gtp_ies:order 15;
		gtp:intsancenum 0;
	}
	container signalling_priority_indication {
		uses gtp_ies:signalling_priority_indication;
		gtp_ies:order 16;
		gtp:intsancenum 0;
	}
	container change_to_report_flags {
		uses gtp_ies:change_to_report_flags;
		gtp_ies:order 17;
		gtp:intsancenum 0;
	}
	container local_home_network_id {
		uses gtp_ies:fqdn;
		gtp_ies:order 18;
		gtp:intsancenum 1;
	}
	container presence_reporting_area_action {
		uses gtp_ies:presence_reporting_area_action;
		gtp_ies:order 19;
		gtp:intsancenum 0;
	}
	container wlan_offloadability_indication {
		uses gtp_ies:wlan_offloadability_indication;
		gtp_ies:order 20;
		gtp:intsancenum 0;
	}
	container remote_ue_context_connected {
		uses gtp_ies:remote_ue_context;
		gtp_ies:order 21;
		gtp:intsancenum 0;
	}
	container pdn_type {
		uses gtp_ies:pdn_type;
		gtp_ies:order 22;
		gtp:intsancenum 0;
	}
	container header_compression_configuration {
		uses gtp_ies:header_compression_configuration;
		gtp_ies:order 23;
		gtp:intsancenum 0;
	}
}
grouping context_response__bearer_context {
	gtp_ies:ie-type 93
;
	gtp:containingMessage 131;
	container eps_bearer_id {
		uses gtp_ies:ebi;
		gtp_ies:order 1;
		gtp:iemandatory;
		gtp:intsancenum 0;
	}
	container tft {
		uses gtp_ies:bearer_tft;
		gtp_ies:order 2;
		gtp:intsancenum 0;
	}
	container sgw_s1s4s12s11_ip_address_and_teid_for_user_plane {
		uses gtp_ies:fteid;
		gtp_ies:order 3;
		gtp:intsancenum 0;
	}
	container pgw_s5s8_ip_address_and_teid_for_user_plane {
		uses gtp_ies:fteid;
		gtp_ies:order 4;
		gtp:intsancenum 1;
	}
	container bearer_level_qos {
		uses gtp_ies:bearer_qos;
		gtp_ies:order 5;
		gtp:iemandatory;
		gtp:intsancenum 0;
	}
	container bss_container {
		uses gtp_ies:fcontainer;
		gtp_ies:order 6;
		gtp:intsancenum 0;
	}
	container transaction_identifier {
		uses gtp_ies:ti;
		gtp_ies:order 7;
		gtp:intsancenum 0;
	}
	container sgw_s11_ip_address_and_teid_for_user_plane {
		uses gtp_ies:fteid;
		gtp_ies:order 8;
		gtp:intsancenum 2;
	}
}
grouping context_response__remote_ue_context_connected {
	gtp_ies:ie-type 191;
	gtp:containingMessage 131;
	container remote_user_id {
		uses gtp_ies:remote_user_id;
		gtp_ies:order 1;
		gtp:iemandatory;
		gtp:intsancenum 0;
		description "See subclause 8.123 for the description and use of this parameter
";
	}
	container remote_ue_ip_information {
		uses gtp_ies:remote_ue_ip_information;
		gtp_ies:order 2;
		gtp:iemandatory;
		gtp:intsancenum 0;
		description "See subclause 8.124 for the description and use of this parameter
";
	}
}
grouping context_response__mmesgsn_ue_scef_pdn_connections {
	gtp_ies:ie-type x;
	gtp:containingMessage 131;
	container apn {
		uses gtp_ies:apn;
		gtp_ies:order 1;
		gtp:iemandatory;
		gtp:intsancenum 0;
	}
	container default_eps_bearer_id {
		uses gtp_ies:ebi;
		gtp_ies:order 2;
		gtp:iemandatory;
		gtp:intsancenum 0;
		description "This IE identifies the default bearer of the SCEF PDN Connection.
";
	}
	container scef_id {
		uses gtp_ies:node_identifier;
		gtp_ies:order 3;
		gtp:iemandatory;
		gtp:intsancenum 0;
		description "This IE shall include the SCEF Identifier and the SCEF Realm for the APN.
";
	}
}
grouping context_acknowledge {
	gtp:messageType "acknowledge";
	container cause {
		uses gtp_ies:cause;
		gtp_ies:order 1;
		gtp:iemandatory;
		gtp:intsancenum 0;
	}
	container indication_flags {
		uses gtp_ies:indication;
		gtp_ies:order 2;
		gtp:intsancenum 0;
	}
	container forwarding_fteid {
		uses gtp_ies:fteid;
		gtp_ies:order 3;
		gtp:intsancenum 0;
	}
	container bearer_contexts {
		uses gtp_ies:bearer_context_;
		gtp_ies:order 4;
		gtp:intsancenum 0;
	}
	container sgsn_number {
		uses gtp_ies:node_number;
		gtp_ies:order 5;
		gtp:intsancenum 0;
	}
	container mme_number_for_mt_sms {
		uses gtp_ies:node_number;
		gtp_ies:order 6;
		gtp:intsancenum 1;
	}
	container sgsn_identifier_for_mt_sms {
		uses gtp_ies:node_identifier;
		gtp_ies:order 7;
		gtp:intsancenum 0;
	}
	container mme_identifier_for_mt_sms {
		uses gtp_ies:node_identifier;
		gtp_ies:order 8;
		gtp:intsancenum 1;
	}
	container private_extension {
		uses gtp_ies:private_extension;
		gtp_ies:order 9;
	}
}
grouping context_acknowledge__bearer_context {
	gtp_ies:ie-type 93;
	gtp:containingMessage 132;
	container eps_bearer_id {
		uses gtp_ies:ebi;
		gtp_ies:order 1;
		gtp:iemandatory;
		gtp:intsancenum 0;
	}
	container forwarding_fteid {
		uses gtp_ies:fteid;
		gtp_ies:order 2;
		gtp:iemandatory;
		gtp:intsancenum 0;
		description "The interface type of the Forwarding F-TEID should be set to either: 
23 (SGW GTP-U interface for DL data forwarding) for indirect forwarding, 
0 ( S1-U eNodeB GTP-U interface) or 3 (S12 RNC GTP-U interface), if the eNB or RNC supports such forwarding, or
15 (S4 SGSN GTP-U interface).
";
	}
}
grouping identification_request {
	gtp:messageType "request";
	container guti {
		uses gtp_ies:guti;
		gtp_ies:order 1;
		gtp:intsancenum 0;
	}
	container packet_tmsi {
		uses gtp_ies:ptmsi;
		gtp_ies:order 3;
		gtp:intsancenum 0;
	}
	container ptmsi_signature {
		uses gtp_ies:ptmsi_signature;
		gtp_ies:order 4;
		gtp:intsancenum 0;
	}
	container complete_attach_request_message {
		uses gtp_ies:complete_request_message;
		gtp_ies:order 5;
		gtp:intsancenum 0;
	}
	container address_for_control_plane {
		uses gtp_ies:ip_address;
		gtp_ies:order 6;
		gtp:intsancenum 0;
	}
	container udp_source_port_number {
		uses gtp_ies:port_number;
		gtp_ies:order 7;
		gtp:intsancenum 0;
	}
	container hop_counter {
		uses gtp_ies:hop_counter;
		gtp_ies:order 8;
		gtp:intsancenum 0;
	}
	container target_plmn_id {
		uses gtp_ies:serving_network;
		gtp_ies:order 9;
		gtp:intsancenum 0;
	}
	container private_extension {
		uses gtp_ies:private_extension;
		gtp_ies:order 10;
	}
}
grouping identification_response {
	gtp:messageType "response";
	container cause {
		uses gtp_ies:cause;
		gtp_ies:order 1;
		gtp:iemandatory;
		gtp:intsancenum 0;
	}
	container imsi {
		uses gtp_ies:imsi;
		gtp_ies:order 2;
		gtp:intsancenum 0;
	}
	container mmesgsn_ue_mm_context {
		uses gtp_ies:mm_context;
		gtp_ies:order 3;
		gtp:intsancenum 0;
	}
	container trace_information {
		uses gtp_ies:trace_information;
		gtp_ies:order 4;
		gtp:intsancenum 0;
	}
	container ue_usage_type {
		uses gtp_ies:integer_number;
		gtp_ies:order 5;
		gtp:intsancenum 0;
	}
	container monitoring_event_information {
		uses gtp_ies:monitoring_event_information;
		gtp_ies:order 6;
		gtp:intsancenum 0;
	}
	container private_extension {
		uses gtp_ies:private_extension;
		gtp_ies:order 7;
	}
}
grouping forward_access_context_notification {
	gtp:messageType "notification";
	container rab_contexts {
		uses gtp_ies:rab_context_;
		gtp_ies:order 1;
		gtp:intsancenum 0;
		description "This IE shall be included for S16 only. Several IEs with this type and instance values shall be included as necessary to represent a list of Bearers.
For each RAB context in the received RANAP message, the old SGSN shall include this IE in the message.
";
	}
	container source_rnc_pdcp_context_info {
		uses gtp_ies:source_rnc_pdcp_context_info;
		gtp_ies:order 2;
		gtp:intsancenum 0;
		description "If available, the old SGSN shall include an Source RNC PDCP context info in the message.
";
	}
	container pdu_numbers {
		uses gtp_ies:pdu_numbers;
		gtp_ies:order 3;
		gtp:intsancenum 0;
		description "This IE only applies to S16. The old SGSN shall include this IE in the message if the acknowledged peer-to-peer LLC operation is used for the Bearer Context or when delivery order is set in the Bearer Context QoS profile in A/Gb mode to Iu/A/Gb mode PS handover.
";
	}
	container eutran_transparent_container {
		uses gtp_ies:fcontainer;
		gtp_ies:order 4;
		gtp:intsancenum 0;
		description "This IE shall be included over S10 to contain the eNB Status Transfer Transparent Container as specified in3GPP TS 36.413 [10].
Container Type shall be set to 3.
";
	}
	container private_extension {
		uses gtp_ies:private_extension;
		gtp_ies:order 5;
	}
}
grouping forward_access_context_acknowledge {
	gtp:messageType "acknowledge";
	container cause {
		uses gtp_ies:cause;
		gtp_ies:order 1;
		gtp:iemandatory;
		gtp:intsancenum 0;
	}
	container private_extension {
		uses gtp_ies:private_extension;
		gtp_ies:order 2;
	}
}
grouping detach_notification {
	gtp:messageType "notification";
	container cause {
		uses gtp_ies:cause;
		gtp_ies:order 1;
		gtp:iemandatory;
		gtp:intsancenum 0;
	}
	container detach_type {
		uses gtp_ies:detach_type;
		gtp_ies:order 2;
		gtp:intsancenum 0;
		description "This IE shall be included by SGSN when the Cause indicates Complete Detach for the combined IMSI/EPS attached UE.
";
	}
	container private_extension {
		uses gtp_ies:private_extension;
		gtp_ies:order 3;
	}
}
grouping detach_acknowledge {
	gtp:messageType "acknowledge";
	container cause {
		uses gtp_ies:cause;
		gtp_ies:order 1;
		gtp:iemandatory;
		gtp:intsancenum 0;
	}
	container recovery {
		uses gtp_ies:recovery;
		gtp_ies:order 2;
		gtp:intsancenum 0;
	}
	container private_extension {
		uses gtp_ies:private_extension;
		gtp_ies:order 3;
	}
}
grouping relocation_cancel_request {
	gtp:messageType "request";
	gtp:messageTypeValue 139;
	container imsi {
		uses gtp_ies:imsi;
		gtp_ies:order 1;
		gtp:intsancenum 0;
		description "The IMSI shall be included in the message except for the case:
-	If the UE is emergency attached and the UE is UICCless.
The IMSI shall be included in the message but not used as an identifier
if UE is emergency attached but IMSI is not authenticated.
";
	}
	container me_identity {
		uses gtp_ies:mei;
		gtp_ies:order 2;
		gtp:intsancenum 0;
		description "The MME/SGSN/AMF shall include the ME Identity (MEI) IE:
-	If the UE is emergency attached and the UE is UICCless
-	If the UE is emergency attached and the IMSI is not authenticated
";
	}
	container indication_flags {
		uses gtp_ies:indication;
		gtp_ies:order 3;
		gtp:intsancenum 0;
		description "This IE shall be included if any one of the applicable flags is set to 1.
Applicable flags are:
Unauthenticated IMSI: This flag shall be set to 1 if the IMSI present in the message is not authenticated and is for an emergency attached UE.
";
	}
	container ranap_cause {
		uses gtp_ies:fcause;
		gtp_ies:order 4;
		gtp:intsancenum 0;
		description "This IE shall be present in the case of SRNS relocation cancel procedure. It shall contain the cause value received from the source RNC in the Relocation Cancel message received over the Iu interface.
";
	}
	container private_extension {
		uses gtp_ies:private_extension;
		gtp_ies:order 5;
	}
}
grouping relocation_cancel_response {
	gtp:messageType "response";
	gtp:messageTypeValue 140;
	container cause {
		uses gtp_ies:cause;
		gtp_ies:order 1;
		gtp:iemandatory;
		gtp:intsancenum 0;
	}
	container private_extension {
		uses gtp_ies:private_extension;
		gtp_ies:order 2;
	}
}
grouping configuration_transfer_tunnel_message {
	gtp:messageType "request";
	container eutran_transparent_container {
		uses gtp_ies:fcontainer;
		gtp_ies:order 1;
		gtp:iemandatory;
		gtp:intsancenum 0;
		description "This IE shall contain the SON Configuration Transfer as specified in 3GPP TS 36.413 [10].
Container Type shall be set to 3.
";
	}
	container target_enodeb_id {
		uses gtp_ies:target_identification;
		gtp_ies:order 2;
		gtp:iemandatory;
		gtp:intsancenum 0;
		description "This IE shall contain the ID of the target eNodeB
";
	}
}
grouping ran_information_relay {
	gtp:messageType "relay";
	container bss_container {
		uses gtp_ies:fcontainer;
		gtp_ies:order 1;
		gtp:iemandatory;
		gtp:intsancenum 0;
		description "All information elements from the BSSGP RIM PDU, starting from and including the BSSGP PDU type, shall be contained within the BSS Container and forwarded to the destination MME/SGSN in the RAN Information Relay message. The Container Type shall be set to 2.
";
	}
	container rim_routing_address {
		uses gtp_ies:target_identification;
		gtp_ies:order 2;
		gtp:intsancenum 0;
		description "This IE shall be included if the RIM Routing Address information is included in the message sent from the source RAN node.
This IE identifies the destination RAN node where the RAN Information needs to be relayed to. It contains: 
the destination RNC Identity when the target is GERAN Iu mode or UTRAN;  or
the destination Cell Identity when the target is GERAN; or 
the Target eNodeB ID when the target is E-UTRAN.
";
	}
	container private_extension {
		uses gtp_ies:private_extension;
		gtp_ies:order 3;
		description "None
";
	}
}
grouping isr_status_indication {
	gtp:messageType "indication";
	container action_indication {
		uses gtp_ies:action_indication;
		gtp_ies:order 1;
		gtp:iemandatory;
		gtp:intsancenum 0;
		description "This IE shall include one of the applicable Values:
Deactivation Indication: If the value is set to 1, this indicates a request to the ISR associated MME/SGSN to deactivate ISR and remove the UE resource locally. See 3GPP TS 23.007 [17].
Paging Indication: If the value is set to 2, this indicates a request to the ISR associated MME/SGSN to page the UE in IDLE state. See 3GPP TS 23.007 [17].
Paging Stop Indication: If the value is set to 3, this indicates to the ISR associated MME/SGSN to stop paging the UE. See 3GPP TS 23.380 [61].
";
	}
	container private_extension {
		uses gtp_ies:private_extension;
		gtp_ies:order 2;
	}
}
grouping ue_registration_query_request {
	gtp:messageType "request";
	gtp:messageTypeValue 158;
	container imsi {
		uses gtp_ies:imsi;
		gtp_ies:order 1;
		gtp:iemandatory;
		gtp:intsancenum 0;
	}
	container private_extension {
		uses gtp_ies:private_extension;
		gtp_ies:order 2;
	}
}
grouping ue_registration_query_response {
	gtp:messageType "response";
	gtp:messageTypeValue 159;
	container cause {
		uses gtp_ies:cause;
		gtp_ies:order 1;
		gtp:iemandatory;
		gtp:intsancenum 0;
	}
	container imsi {
		uses gtp_ies:imsi;
		gtp_ies:order 2;
		gtp:iemandatory;
		gtp:intsancenum 0;
	}
	container selected_core_network_operator_identifier {
		uses gtp_ies:plmn_id;
		gtp_ies:order 3;
		gtp:iemandatory;
		gtp:intsancenum 0;
	}
	container private_extension {
		uses gtp_ies:private_extension;
		gtp_ies:order 4;
	}
}
grouping alert_mme_acknowledge {
	gtp:messageType "acknowledge";
	gtp:messageTypeValue 154;
	container cause {
		uses gtp_ies:cause;
		gtp_ies:order 1;
		gtp:iemandatory;
		gtp:intsancenum 0;
	}
	container private_extension {
		uses gtp_ies:private_extension;
		gtp_ies:order 2;
	}
}
grouping ue_activity_acknowledge {
	gtp:messageType "acknowledge";
	gtp:messageTypeValue 156;
	container cause {
		uses gtp_ies:cause;
		gtp_ies:order 1;
		gtp:iemandatory;
		gtp:intsancenum 0;
	}
	container private_extension {
		uses gtp_ies:private_extension;
		gtp_ies:order 2;
	}
}
grouping create_forwarding_tunnel_request {
	gtp:messageType "request";
	container s103_pdn_data_forwarding_info {
		uses gtp_ies:s103pdf;
		gtp_ies:order 1;
		gtp:iemandatory;
		gtp:intsancenum 0;
		description "The MME shall include the forwarding Infomation for all PDN connections of the UE requesting data forwarding towards the HSGW in the message as S103 PDN Data Forwarding Info information elements. For each of those PDN Connections, an IE with the same type and instance value shall be included.
The Serving GW shall forward downlink data to the HSGW via the GRE tunnel identified by the HSGW Address and HSGW GRE Key included in this information element when it receives downlink data forwarded from the eNodeB belonging to the corresponding EPS bearers of the PDN connection.
";
	}
	container private_extension {
		uses gtp_ies:private_extension;
		gtp_ies:order 2;
	}
}
grouping create_forwarding_tunnel_response {
	gtp:messageType "response";
	container cause {
		uses gtp_ies:cause;
		gtp_ies:order 1;
		gtp:iemandatory;
		gtp:intsancenum 0;
	}
	container s1u_data_forwarding_info {
		uses gtp_ies:s1udf;
		gtp_ies:order 2;
		gtp:intsancenum 0;
		description "S1-U Data Forwarding Info shall be included in the message if the Cause contains the value Request accepted. For each EPS bearer requesting data forwarding which is included in the S103 PDN Data Forwarding Info fields of corresponding Create Forwarding Tunnel Request message, the Serving GW shall assign a Serving GW S1-U Address and Serving GW S1-U TEID pair and included it in the response message as S1-U Data Forwarding Info information element. For each of those EPS bearers, an IE with the same type and instance value shall be included.
The eNodeB shall forward downlink data of the EPS bearer to the Serving GW via the GTP-U tunnel identified by the Serving GW S1-U Address and Serving GW S1-U TEID.
";
	}
	container private_extension {
		uses gtp_ies:private_extension;
		gtp_ies:order 3;
	}
}
grouping delete_pdn_connection_set_response {
	gtp:messageType "response";
	container cause {
		uses gtp_ies:cause;
		gtp_ies:order 1;
		gtp:iemandatory;
		gtp:intsancenum 0;
	}
	container recovery {
		uses gtp_ies:recovery;
		gtp_ies:order 2;
		gtp:intsancenum 0;
		description "This IE shall be included if contacting the peer for the first time 
";
	}
	container private_extension {
		uses gtp_ies:private_extension;
		gtp_ies:order 3;
		description "This IE may be sent on the S2a, S2b, S5, S8 and S11 interfaces.
";
	}
}
grouping update_pdn_connection_set_request {
	gtp:messageType "request";
	container mmefqcsid {
		uses gtp_ies:fqcsid;
		gtp_ies:order 1;
		gtp:intsancenum 0;
		description "This IE shall be included for MME relocation without SGW relocation according to the requirements in 3GPP TS 23.007 [17].
";
	}
	container sgwfqcsid {
		uses gtp_ies:fqcsid;
		gtp_ies:order 2;
		gtp:intsancenum 1;
		description "This IE shall be included for MME relocation without SGW relocation according to the requirements in 3GPP TS 23.007 [17].
";
	}
	container private_extension {
		uses gtp_ies:private_extension;
		gtp_ies:order 3;
	}
}
grouping update_pdn_connection_set_response {
	gtp:messageType "response";
	container cause {
		uses gtp_ies:cause;
		gtp_ies:order 1;
		gtp:iemandatory;
		gtp:intsancenum 0;
	}
	container pgwfqcsid {
		uses gtp_ies:fqcsid;
		gtp_ies:order 2;
		gtp:intsancenum 0;
		description "This IE shall be included for MME relocation without SGW relocation according to the requirements in 3GPP TS 23.007 [17].
";
	}
	container recovery {
		uses gtp_ies:recovery;
		gtp_ies:order 3;
		gtp:intsancenum 0;
		description "This IE shall be included if contacting the peer for the first time 
";
	}
	container private_extension {
		uses gtp_ies:private_extension;
		gtp_ies:order 4;
	}
}
grouping pgw_restart_notification {
	gtp:messageType "notification";
	gtp:messageTypeValue 179;
	container pgw_s5s8_ip_address_for_control_plane_or_pmip {
		uses gtp_ies:ip_address;
		gtp_ies:order 1;
		gtp:iemandatory;
		gtp:intsancenum 0;
	}
	container sgw_s11s4_ip_address_for_control_plane {
		uses gtp_ies:ip_address;
		gtp_ies:order 2;
		gtp:iemandatory;
		gtp:intsancenum 1;
	}
	container cause {
		uses gtp_ies:cause;
		gtp_ies:order 3;
		gtp:intsancenum 0;
		description "The SGW shall send the Cause IE with the value PGW not responding if it sends the PGW Restart Notification to notify that the peer PGW has failed and not restarted. 
";
	}
	container private_extension {
		uses gtp_ies:private_extension;
		gtp_ies:order 4;
	}
}
grouping pgw_restart_notification_acknowledge {
	gtp:messageType "acknowledge";
	gtp:messageTypeValue 180;
	container cause {
		uses gtp_ies:cause;
		gtp_ies:order 1;
		gtp:iemandatory;
		gtp:intsancenum 0;
	}
	container private_extension {
		uses gtp_ies:private_extension;
		gtp_ies:order 2;
	}
}
grouping pgw_downlink_triggering_notification {
	gtp:messageType "notification";
	gtp:messageTypeValue 103;
	container imsi {
		uses gtp_ies:imsi;
		gtp_ies:order 1;
		gtp:iemandatory;
		gtp:intsancenum 0;
	}
	container mmes4sgsn_identifier {
		uses gtp_ies:ip_address;
		gtp_ies:order 2;
		gtp:intsancenum 0;
	}
	container pgw_s5_fteid_for_gtp_or_pmip_control_plane {
		uses gtp_ies:fteid;
		gtp_ies:order 3;
		gtp:intsancenum 0;
	}
	container private_extension {
		uses gtp_ies:private_extension;
		gtp_ies:order 4;
	}
}
grouping pgw_downlink_triggering_acknowledge {
	gtp:messageType "acknowledge";
	gtp:messageTypeValue 104;
	container cause {
		uses gtp_ies:cause;
		gtp_ies:order 1;
		gtp:iemandatory;
		gtp:intsancenum 0;
	}
	container imsi {
		uses gtp_ies:imsi;
		gtp_ies:order 2;
		gtp:intsancenum 0;
		description "This IE shall be included on S11/S4 interface if the Cause is indicating the rejection value Context Not Found and if the MME/S4-SGSN identifier is included in the corresponding PGW Downlink Triggering Notification message.
";
	}
	container mmes4sgsn_identifier {
		uses gtp_ies:ip_address;
		gtp_ies:order 3;
		gtp:intsancenum 0;
		description "This IE shall be included on S11/S4 interface if the Cause is indicating the rejection value Context Not Found and if the MME/S4-SGSN identifier is included in the corresponding PGW Downlink Triggering Notification message.
";
	}
	container private_extension {
		uses gtp_ies:private_extension;
		gtp_ies:order 4;
	}
}
grouping trace_session_activation {
	gtp:messageType "activation";
	container imsi {
		uses gtp_ies:imsi;
		gtp_ies:order 1;
		gtp:intsancenum 0;
	}
	container trace_information {
		uses gtp_ies:trace_information;
		gtp_ies:order 2;
		gtp:iemandatory;
		gtp:intsancenum 0;
	}
	container me_identity {
		uses gtp_ies:mei;
		gtp_ies:order 3;
		gtp:intsancenum 0;
	}
}
grouping trace_session_deactivation {
	gtp:messageType "activation";
	container trace_reference {
		uses gtp_ies:trace_reference;
		gtp_ies:order 1;
		gtp:iemandatory;
		gtp:intsancenum 0;
	}
}
grouping mbms_session_start_request {
	gtp:messageType "request";
	container sender_fteid_for_control_plane {
		uses gtp_ies:fteid;
		gtp_ies:order 1;
		gtp:iemandatory;
		gtp:intsancenum 0;
	}
	container temporary_mobile_group_identity {
		uses gtp_ies:tmgi;
		gtp_ies:order 2;
		gtp:iemandatory;
		gtp:intsancenum 0;
	}
	container mbms_session_duration {
		uses gtp_ies:mbms_session_duration;
		gtp_ies:order 3;
		gtp:iemandatory;
		gtp:intsancenum 0;
	}
	container mbms_service_area {
		uses gtp_ies:mbms_service_area;
		gtp_ies:order 4;
		gtp:iemandatory;
		gtp:intsancenum 0;
	}
	container mbms_session_identifier {
		uses gtp_ies:mbms_session_identifier;
		gtp_ies:order 5;
		gtp:intsancenum 0;
	}
	container mbms_flow_identifier {
		uses gtp_ies:mbms_flow_identifier;
		gtp_ies:order 6;
		gtp:intsancenum 0;
	}
	container qos_profile {
		uses gtp_ies:bearer_qos;
		gtp_ies:order 7;
		gtp:iemandatory;
		gtp:intsancenum 0;
	}
	container mbms_ip_multicast_distribution {
		uses gtp_ies:mbms_ip_multicast_distribution;
		gtp_ies:order 8;
		gtp:iemandatory;
		gtp:intsancenum 0;
	}
	container recovery {
		uses gtp_ies:recovery;
		gtp_ies:order 9;
		gtp:intsancenum 0;
	}
	container mbms_time_to_data_transfer {
		uses gtp_ies:mbms_time_to_data_transfer;
		gtp_ies:order 10;
		gtp:intsancenum 0;
	}
	container mbms_data_transfer_start {
		uses gtp_ies:absolute_time_of_mbms_data_transfer;
		gtp_ies:order 11;
		gtp:intsancenum 0;
	}
	container mbms_flags {
		uses gtp_ies:mbms_flags;
		gtp_ies:order 12;
		gtp:intsancenum 0;
	}
	container mbms_alternative_ip_multicast_distribution {
		uses gtp_ies:mbms_ip_multicast_distribution;
		gtp_ies:order 13;
		gtp:intsancenum 1;
	}
	container mbms_cell_list {
		uses gtp_ies:ecgilist;
		gtp_ies:order 14;
		gtp:intsancenum 0;
	}
	container private_extension {
		uses gtp_ies:private_extension;
		gtp_ies:order 15;
	}
}
grouping mbms_session_start_response {
	gtp:messageType "response";
	container cause {
		uses gtp_ies:cause;
		gtp_ies:order 1;
		gtp:iemandatory;
		gtp:intsancenum 0;
	}
	container sender_fteid_for_control_plane {
		uses gtp_ies:fteid;
		gtp_ies:order 2;
		gtp:iemandatory;
		gtp:intsancenum 0;
	}
	container mbms_distribution_acknowledge {
		uses gtp_ies:mbms_distribution_messageType_acknowledge;
		gtp_ies:order 3;
		gtp:intsancenum 0;
		description "This IE shall be included on the Sn interface.
";
	}
	container snu_sgsn_fteid {
		uses gtp_ies:fteid;
		gtp_ies:order 4;
		gtp:intsancenum 1;
		description "This IE shall be included on the Sn interface if some RNCs have not accepted IP multicast distribution.
";
	}
	container recovery {
		uses gtp_ies:recovery;
		gtp_ies:order 5;
		gtp:intsancenum 0;
		description "This IE shall be included if contacting the peer for the first time.
";
	}
	container private_extension {
		uses gtp_ies:private_extension;
		gtp_ies:order 6;
	}
}
grouping mbms_session_update_request {
	gtp:messageType "request";
	container mbms_service_area {
		uses gtp_ies:mbms_service_area;
		gtp_ies:order 1;
		gtp:intsancenum 0;
	}
	container temporary_mobile_group_identity {
		uses gtp_ies:tmgi;
		gtp_ies:order 2;
		gtp:iemandatory;
		gtp:intsancenum 0;
	}
	container sender_fteid_for_control_plane {
		uses gtp_ies:fteid;
		gtp_ies:order 3;
		gtp:intsancenum 0;
	}
	container mbms_session_duration {
		uses gtp_ies:mbms_session_duration;
		gtp_ies:order 4;
		gtp:iemandatory;
		gtp:intsancenum 0;
	}
	container qos_profile {
		uses gtp_ies:bearer_qos;
		gtp_ies:order 5;
		gtp:iemandatory;
		gtp:intsancenum 0;
	}
	container mbms_session_identifier {
		uses gtp_ies:mbms_session_identifier;
		gtp_ies:order 6;
		gtp:intsancenum 0;
	}
	container mbms_flow_identifier {
		uses gtp_ies:mbms_flow_identifier;
		gtp_ies:order 7;
		gtp:intsancenum 0;
	}
	container mbms_time_to_data_transfer {
		uses gtp_ies:mbms_time_to_data_transfer;
		gtp_ies:order 8;
		gtp:intsancenum 0;
	}
	container mbms_data_transfer_start__update__stop {
		uses gtp_ies:absolute_time_of_mbms_data_transfer;
		gtp_ies:order 9;
		gtp:intsancenum 0;
	}
	container mbms_cell_list {
		uses gtp_ies:ecgi_list;
		gtp_ies:order 10;
		gtp:intsancenum 0;
	}
	container private_extension {
		uses gtp_ies:private_extension;
		gtp_ies:order 11;
	}
}
grouping mbms_session_update_response {
	gtp:messageType "response";
	container cause {
		uses gtp_ies:cause;
		gtp_ies:order 1;
		gtp:iemandatory;
		gtp:intsancenum 0;
	}
	container mbms_distribution_acknowledge {
		uses gtp_ies:mbms_distribution_messageType_acknowledge;
		gtp_ies:order 2;
		gtp:intsancenum 0;
		description "This IE shall be included on the Sn interface if service area is changed.
";
	}
	container snu_sgsn_fteid {
		uses gtp_ies:fteid;
		gtp_ies:order 3;
		gtp:intsancenum 0;
		description "This IE shall be included on the Sn interface if any of the newly added RNCs have not accepted IP multicast distribution.
";
	}
	container recovery {
		uses gtp_ies:recovery;
		gtp_ies:order 4;
		gtp:intsancenum 0;
		description "This IE shall be included if contacting the peer for the first time.
";
	}
	container private_extension {
		uses gtp_ies:private_extension;
		gtp_ies:order 5;
	}
}
grouping mbms_session_stop_request {
	gtp:messageType "request";
	container mbms_flow_identifier {
		uses gtp_ies:mbms_flow_identifier;
		gtp_ies:order 1;
		gtp:intsancenum 0;
	}
	container mbms_data_transfer_stop {
		uses gtp_ies:absolute_time_of_mbms_data_transfer;
		gtp_ies:order 2;
		gtp:intsancenum 0;
	}
	container mbms_flags {
		uses gtp_ies:mbms_flags;
		gtp_ies:order 3;
		gtp:intsancenum 0;
	}
	container private_extension {
		uses gtp_ies:private_extension;
		gtp_ies:order 4;
	}
}
grouping mbms_session_stop_response {
	gtp:messageType "response";
	container cause {
		uses gtp_ies:cause;
		gtp_ies:order 1;
		gtp:iemandatory;
		gtp:intsancenum 0;
	}
	container recovery {
		uses gtp_ies:recovery;
		gtp_ies:order 2;
		gtp:intsancenum 0;
		description "This IE shall be included if contacting the peer for the first time.
";
	}
	container private_extension {
		uses gtp_ies:private_extension;
		gtp_ies:order 3;
	}
}



}
