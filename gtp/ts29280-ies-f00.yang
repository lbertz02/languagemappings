module ts29280-ies-f00 {

namespace "urn:onf:params:xml:ns:yang:ts29280:f:messages";
prefix "svies";

import ts29274-ies-f40 {	
	prefix "gtp_ies";
}

description "Information Elements defined in TS 29.280 that
	are required for TS 29.274 (f40).  This document is
	based upon TS 29.280 f00 which was defined at the
	time of TS 29.274 f40's creation.

   Copyright 2018 Lyle Bertz.

   Licensed under the Apache License, Version 2.0 (the \"License\");
   you may not use this file except in compliance with the License.
   You may obtain a copy of the License at

       http://www.apache.org/licenses/LICENSE-2.0

   Unless required by applicable law or agreed to in writing, software
   distributed under the License is distributed on an \"AS IS\" BASIS,
   WITHOUT WARRANTIES OR CONDITIONS OF ANY KIND, either express or implied.
   See the License for the specific language governing permissions and
   limitations under the License.";

// NOTE - this module only fills in what is needed for 29274 messages

grouping stn_sr {
	gtp_ies:ie-type 51;
	leaf nanpi {
		gtp_ies:order 4;
		type binary {
			length "8";
		}
	}
	leaf-list number_digit {
		min-elements 1;
		gtp_ies:order 5;
		type binary {
			length "4";
		}
	}
	leaf filler {
		gtp_ies:order 6;
		type binary {
			length "4";
		}
		gtp_ies:defval "1111"; 
	}
}

}
